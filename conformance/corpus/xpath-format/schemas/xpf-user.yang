// SPDX-License-Identifier: BSD-3-Clause
// Hand-written conformance fixture (this repo): XPath query formats (#171); imports xpf-rev in a
// revision other than the implemented one.
module xpf-user {
  yang-version 1.1;
  namespace "urn:vibe-ports:yang:conformance:xpf-user";
  prefix u;

  import xpf-rev {
    prefix r;
    revision-date 2020-01-01;
  }
  leaf w {
    type string;
  }
}
