// SPDX-License-Identifier: BSD-3-Clause
// Hand-written conformance fixture (this repo).
module xcm-augment-a {
  yang-version 1.1;
  namespace "urn:vibe-ports:yang:xpath-cur-mod:augment-a";
  prefix xaa;

  import xcm-base { prefix xb; }
  import xcm-augment-m { prefix xam; }

  identity x { base xb:root; }

  augment "/xam:target" {
    leaf id {
      type identityref { base xb:root; }
      must "derived-from-or-self(., 'x')" {
        error-message "the identity must be x in the augmenting module";
        error-app-tag "xcm-augment-module";
      }
    }
  }
}
