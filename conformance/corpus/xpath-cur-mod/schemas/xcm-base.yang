// SPDX-License-Identifier: BSD-3-Clause
// Hand-written conformance fixture (this repo).
module xcm-base {
  yang-version 1.1;
  namespace "urn:vibe-ports:yang:xpath-cur-mod:base";
  prefix xb;

  identity root;
  identity g-branch { base root; }
  identity m-branch { base root; }
}
