// SPDX-License-Identifier: BSD-3-Clause
// Hand-written conformance fixture (this repo).
module xcm-cur-m {
  yang-version 1.1;
  namespace "urn:vibe-ports:yang:xpath-cur-mod:cur-m";
  prefix xcm;

  import xcm-base { prefix xb; }
  import xcm-cur-g { prefix xcg; }

  identity local { base xb:root; }

  container current {
    uses xcg:current-module-grouping;
  }
}
