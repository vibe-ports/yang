// SPDX-License-Identifier: BSD-3-Clause
// Hand-written conformance fixture (this repo).
module xcm-node-m {
  yang-version 1.1;
  namespace "urn:vibe-ports:yang:xpath-cur-mod:node-m";
  prefix xnm;

  import xcm-node-g { prefix xng; }

  container node-step {
    uses xng:node-step-grouping;
  }
}
