// SPDX-License-Identifier: BSD-3-Clause
// Hand-written conformance fixture (this repo).
module xcm-literal-m {
  yang-version 1.1;
  namespace "urn:vibe-ports:yang:xpath-cur-mod:literal-m";
  prefix xlm;

  import xcm-base { prefix xb; }
  import xcm-literal-g { prefix xlg; }

  identity local { base xb:root; }

  container literal {
    uses xlg:identity-literal-grouping;
  }
}
