// SPDX-License-Identifier: BSD-3-Clause
// Hand-written conformance fixture (this repo).
module xcm-cur-g {
  yang-version 1.1;
  namespace "urn:vibe-ports:yang:xpath-cur-mod:cur-g";
  prefix xcg;

  import xcm-base { prefix xb; }

  grouping current-module-grouping {
    leaf id {
      type identityref { base xb:root; }
      must "derived-from-or-self(., 'local')" {
        error-message "the identity must be local to the instantiated schema module";
        error-app-tag "xcm-cur-module";
      }
    }
  }
}
