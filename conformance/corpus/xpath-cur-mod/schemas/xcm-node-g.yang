// SPDX-License-Identifier: BSD-3-Clause
// Hand-written conformance fixture (this repo).
module xcm-node-g {
  yang-version 1.1;
  namespace "urn:vibe-ports:yang:xpath-cur-mod:node-g";
  prefix xng;

  grouping node-step-grouping {
    leaf sibling { type string; }
    leaf probe {
      type string;
      must "../sibling = 'ok'" {
        error-message "the sibling in the instantiated module must be selected";
        error-app-tag "xcm-node-module";
      }
    }
  }
}
