// SPDX-License-Identifier: BSD-3-Clause
// Hand-written conformance fixture (this repo).
module xcm-both-m {
  yang-version 1.1;
  namespace "urn:vibe-ports:yang:xpath-cur-mod:both-m";
  prefix xbm;

  import xcm-base { prefix xb; }
  import xcm-both-g { prefix xbg; }

  identity local { base xb:m-branch; }
  identity m-child { base local; }

  container both {
    uses xbg:both-modules-grouping;
  }
}
