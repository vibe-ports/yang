// SPDX-License-Identifier: BSD-3-Clause
// Hand-written conformance fixture (this repo).
module xcm-when-g {
  yang-version 1.1;
  namespace "urn:vibe-ports:yang:xpath-cur-mod:when-g";
  prefix xwg;

  import xcm-base { prefix xb; }

  grouping current-module-when-grouping {
    leaf id {
      type identityref { base xb:root; }
    }
    leaf guarded {
      when "derived-from-or-self(../id, 'local')";
      type string;
    }
  }
}
