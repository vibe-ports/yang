module b {yang-version 1.1;namespace urn:b;prefix b; typedef mybasetype {type string;}typedef mytype {type union {type int8; type mybasetype;}}leaf l {type union {type decimal64 {fraction-digits 2;} type mytype;}}}
