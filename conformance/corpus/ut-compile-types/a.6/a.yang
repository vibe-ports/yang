module a {yang-version 1.1;namespace urn:a;prefix a;identity i; identity j; identity k {base i;}typedef mytype {type identityref {base i;}}leaf l1 {type mytype;} leaf l2 {type identityref {base a:k; base j;}}}
