module a {yang-version 1.1; namespace urn:a;prefix a;feature f; leaf l {type enumeration {enum automin; enum min {value -2147483648;}enum one {if-feature f; value 1;}enum two; enum seven {value 7;}enum eight;}}}
