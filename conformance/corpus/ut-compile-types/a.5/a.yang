module a {namespace urn:a;prefix a;typedef mytype {type instance-identifier {require-instance false;}}leaf l1 {type instance-identifier {require-instance true;}}leaf l2 {type mytype;} leaf l3 {type instance-identifier;}}
