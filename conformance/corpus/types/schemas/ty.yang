module ty {
  yang-version 1.1;
  namespace "urn:vibe-ports:ty";
  prefix ty;

  description "Built-in type edge cases for internal/types (M1-4).";

  container c {
    leaf i8 { type int8 { range "0 .. 50 | 105"; } }
    leaf i32 { type int32; }
    leaf i64 { type int64; }
    leaf u64 { type uint64; }
    leaf d1 { type decimal64 { fraction-digits 1; range "1.5 .. 10"; } }
    leaf d18 { type decimal64 { fraction-digits 18; } }
    leaf s {
      type string {
        length "2 .. 5";
        pattern "[a-z]+";
        pattern "x.*" { modifier invert-match; }
      }
    }
    leaf b { type boolean; }
    leaf e { type empty; }
    leaf en { type enumeration { enum white; enum black { value -1; } } }
    leaf bt { type bits { bit two { position 2; } bit ten { position 10; } } }
    leaf bin { type binary { length "1 .. 3"; } }
  }
}
