module ty9nb {
  yang-version 1.1;
  namespace "urn:vibe-ports:ty9nb";
  prefix nb;

  import ietf-netconf-acm { prefix nacm; }
  import ty9b { prefix t; }

  description "node-instance-identifier default referencing an import-only module (#60).";

  leaf p {
    type nacm:node-instance-identifier;
    default "/t:cb/t:lb";
  }
}
