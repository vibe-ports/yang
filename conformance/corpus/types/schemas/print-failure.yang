// SPDX-License-Identifier: BSD-3-Clause
module print-failure {
  yang-version 1.1;
  namespace "urn:vibe-ports:print-failure";
  prefix pf;

  import ietf-yang-metadata { prefix md; }
  import ietf-yang-types { prefix yang; }

  md:annotation select { type yang:xpath1.0; }

  container c {
    leaf s { type string; }
    leaf xp { type yang:xpath1.0; }
  }
}
