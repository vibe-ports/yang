module T0 {
  yang-version 1.1;
  namespace "urn:tests:T0";
  prefix pref;
typedef my_type{type bits {  bit ten {position 10;} bit eleven; bit two {position 2;} bit twelve;  bit _test-end...;}}leaf port {type my_type;}}
