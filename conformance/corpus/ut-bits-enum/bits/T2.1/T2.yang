module T2 {
  yang-version 1.1;
  namespace "urn:tests:T2";
  prefix pref;
typedef my_type{type bits { bit ten {position 10;} bit eleven; bit two {position 2;} bit twelve;}}leaf port {type my_type;}}
