module rbs {
  yang-version 1.1;
  namespace "urn:rbs";
  prefix rs;

  rpc r4 {
    input {
      leaf in { type string; }
    }
    output {
      leaf before { type string; }
      leaf-list v {
        type uint8;
        max-elements 2;
      }
    }
  }
}
