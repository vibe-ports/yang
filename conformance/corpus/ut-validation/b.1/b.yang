module b {
    namespace urn:tests:b;
    prefix b;
    yang-version 1.1;

    choice choic {
        mandatory true;
        leaf a {
            type string;
        }
        case b {
            leaf l {
                type string;
            }
        }
    }
    leaf c {
        mandatory true;
        type string;
    }
    leaf d {
        type empty;
    }
}
