module twm4 {
    namespace urn:tests:twm4;
    prefix twm4;
    yang-version 1.1;

    container top {
        leaf flag {
            type boolean;
        }
        list item {
            when "../flag = 'true'";
            key "name";
            leaf name { type string; }
            leaf value { type string; }
        }
        leaf checker {
            must "/twm4:top/twm4:item[twm4:name = 'a']/twm4:value = 'expected'" {
                error-app-tag "checker-bad";
                error-message "checker requires item[a]/value=expected";
            }
            type string;
        }
    }
}
