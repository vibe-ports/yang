module a {
  namespace urn:tests:a;
  prefix a;yang-version 1.1;
  feature f1;
  feature f2;
  leaf foo1 {
    type uint16;
    if-feature f1;
  }
  leaf foo2 {
    type uint16;
  }
  container cont {
    leaf foo3 {
      type string;
    }
  }
}
