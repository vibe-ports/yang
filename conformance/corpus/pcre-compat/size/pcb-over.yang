module pcb-over {
  yang-version 1.1;
  namespace "urn:tests:pcb-over";
  prefix pcb-over;
  description "2,000 Unicode letter classes expand to about 1.37 million ranges, well over the 1,048,576-range budget whatever the Go version's Unicode tables.";
  leaf l { type string { pattern '\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}'; } }
}
