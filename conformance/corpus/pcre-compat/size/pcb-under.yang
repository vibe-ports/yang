module pcb-under {
  yang-version 1.1;
  namespace "urn:tests:pcb-under";
  prefix pcb-under;
  description "1,533 Unicode letter classes expand to 1,048,572 ranges.";
  leaf l { type string { pattern '\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}\p{L}'; } }
}
