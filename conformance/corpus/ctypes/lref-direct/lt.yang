module lt {
  yang-version 1.1;
  namespace "urn:vibe-ports:lt";
  prefix lt;

  description "Leafref typedefs with a relative, unprefixed path, used by other modules.";

  typedef ref { type leafref { path "../x"; } }
  typedef u { type union { type leafref { path "../x"; } type boolean; } }
}
