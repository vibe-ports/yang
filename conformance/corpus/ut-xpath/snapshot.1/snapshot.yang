module snapshot {
  yang-version 1.1;
  namespace "urn:snapshot";
  prefix s;

  container top {
    list l {
      key k;
      leaf k { type string; }
      leaf marker { type string; }
      leaf other { type string; }
    }
    leaf ref {
      type leafref { path "../l/marker"; }
    }
  }
}
