module atm {
  yang-version 1.1;
  namespace "urn:atm";
  prefix p;

  container top {
    list l {
      key "k1 k2";
      leaf k1 { type string; }
      leaf k2 { type string; }
      leaf v { type string; }
    }
    leaf ref {
      type leafref { path "../l/v"; }
    }
    leaf x { type string; }
  }
}
