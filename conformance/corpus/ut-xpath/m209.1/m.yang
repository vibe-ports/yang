module m {
  yang-version 1.1;
  namespace "urn:vibe-ports:yang:conformance:issue209:m";
  prefix m;

  container c;

  leaf ref {
    type instance-identifier {
      require-instance false;
    }
  }

  leaf target {
    type string;
  }
}
