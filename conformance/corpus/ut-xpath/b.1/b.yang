module b {
    namespace urn:tests:b;
    prefix b;
    yang-version 1.1;

    list l2 {
        key "a";
        leaf a {
            type uint16;
        }
        leaf b {
            type uint16;
        }
    }
}
