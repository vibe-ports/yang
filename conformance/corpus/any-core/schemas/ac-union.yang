// SPDX-License-Identifier: BSD-3-Clause
module ac-union {
  yang-version 1.1;
  namespace "urn:tests:any-core-union";
  prefix au;

  anydata data;
  leaf-list u { type union { type uint8; type string; } }
}
