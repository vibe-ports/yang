// SPDX-License-Identifier: BSD-3-Clause
module ac-payload {
  yang-version 1.1;
  namespace "urn:tests:any-core-payload";
  prefix ap;

  container c {
    presence "Payload from a different schema context";
    leaf value { type string; }
  }
}
