// SPDX-License-Identifier: BSD-3-Clause
module ac-r10 {
  yang-version 1.1;
  namespace "urn:tests:any-core-r10";
  prefix ar10;

  import ietf-yang-types { prefix yang; }

  leaf-list dates { type yang:date; }

  container a {
    leaf x { type string; }
  }
  container b {
    config false;
    list l {
      leaf v { type string; }
    }
  }
}
