// SPDX-License-Identifier: BSD-3-Clause
// Adapted from libyang v5.8.6 tests/utests/schema/test_tree_schema_compile.c:test_uses.
module uses-grouping-not-found {
  yang-version 1;
  namespace "urn:vibe-ports:yang:conformance:uses-grouping-not-found";
  prefix uses-grouping-not-found;
  uses missinggrp;
}
