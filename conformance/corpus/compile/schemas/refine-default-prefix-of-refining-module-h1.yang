// SPDX-License-Identifier: BSD-3-Clause
// Hand-written conformance fixture (this repo).
module refine-default-prefix-of-refining-module-h1 {
  yang-version 1.1;
  namespace "urn:vibe-ports:yang:conformance:refine-default-prefix-of-refining-module-h1";
  prefix refine-default-prefix-of-refining-module-h1;
  identity b;
  grouping g { leaf x { type identityref { base b; } } }
}
