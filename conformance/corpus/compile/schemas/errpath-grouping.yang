// SPDX-License-Identifier: BSD-3-Clause
// Hand-written conformance fixture (this repo).
module errpath-grouping {
  yang-version 1.1;
  namespace "urn:vibe-ports:yang:conformance:errpath-grouping";
  prefix errpath-grouping;
  container top {
    grouping g { leaf x { type string; mandatory true; default "a"; } }
  }
}
