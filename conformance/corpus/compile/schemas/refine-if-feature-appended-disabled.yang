// SPDX-License-Identifier: BSD-3-Clause
// Hand-written conformance fixture (this repo).
module refine-if-feature-appended-disabled {
  yang-version 1.1;
  namespace "urn:vibe-ports:yang:conformance:refine-if-feature-appended-disabled";
  prefix refine-if-feature-appended-disabled;
  feature f;
  grouping g { leaf x { type string; } leaf y { type string; } }
  uses g { refine x { if-feature f; } }
}
