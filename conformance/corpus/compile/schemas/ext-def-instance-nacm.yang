// SPDX-License-Identifier: BSD-3-Clause
// Hand-written conformance fixture (this repo).
// A NACM extension instance inside an extension definition: the plugin's placement diagnostics
// show the path of the instance.
module ext-def-instance-nacm {
  yang-version 1.1;
  namespace "urn:vibe-ports:yang:conformance:ext-def-instance-nacm";
  prefix edin;
  import ietf-netconf-acm { prefix nacm; }
  extension holder {
    nacm:default-deny-write;
  }
}
