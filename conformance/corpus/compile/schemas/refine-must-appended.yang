// SPDX-License-Identifier: BSD-3-Clause
// Hand-written conformance fixture (this repo).
module refine-must-appended {
  yang-version 1.1;
  namespace "urn:vibe-ports:yang:conformance:refine-must-appended";
  prefix refine-must-appended;
  grouping g { leaf x { type string; must "1"; } }
  uses g { refine x { must "2"; } }
}
