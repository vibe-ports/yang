// SPDX-License-Identifier: BSD-3-Clause
// Hand-written conformance fixture (this repo).
module must-syntax-error {
  yang-version 1.1;
  namespace "urn:vibe-ports:yang:conformance:must-syntax-error";
  prefix must-syntax-error;
  leaf a { type string; must "1 +"; }
}
