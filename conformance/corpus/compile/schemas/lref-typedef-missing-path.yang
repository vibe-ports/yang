// SPDX-License-Identifier: BSD-3-Clause
// Adapted from libyang v5.8.6 tests/utests/schema/test_tree_schema_compile.c:test_type_leafref.
module lref-typedef-missing-path {
  yang-version 1;
  namespace "urn:vibe-ports:yang:conformance:lref-typedef-missing-path";
  prefix lref-typedef-missing-path;
  typedef mytype { type leafref; }
  leaf ref1 { type mytype; }
}
