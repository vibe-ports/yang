// SPDX-License-Identifier: BSD-3-Clause
// Hand-written conformance fixture (this repo).
module ext-annotation-twice {
  yang-version 1.1;
  namespace "urn:vibe-ports:yang:conformance:ext-annotation-twice";
  prefix ext-annotation-twice;
  import ietf-yang-metadata { prefix md; }
  md:annotation foo { type string; }
  md:annotation foo { type uint8; }
}
