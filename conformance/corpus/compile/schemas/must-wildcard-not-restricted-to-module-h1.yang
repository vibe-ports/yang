// SPDX-License-Identifier: BSD-3-Clause
// Adapted from libyang v5.8.6 tests/utests/schema/test_tree_schema_compile.c:test_must.
module must-wildcard-not-restricted-to-module-h1 {
  yang-version 1;
  namespace "urn:vibe-ports:yang:conformance:must-wildcard-not-restricted-to-module-h1";
  prefix must-wildcard-not-restricted-to-module-h1;
  container cont { leaf l { type empty; } list lst { key k; leaf k { type uint8; } } }
}
