// SPDX-License-Identifier: BSD-3-Clause
// Hand-written conformance fixture (this repo).
module aug-base {
  yang-version 1.1;
  namespace "urn:vibe-ports:yang:conformance:aug-base";
  prefix aug-base;
  container c { leaf own { type string; } }
}
