// SPDX-License-Identifier: BSD-3-Clause
// Adapted from libyang v5.8.6 tests/utests/schema/test_tree_schema_compile.c:test_node_choice.
module choice-duplicate-leaf-in-case-and-shorthand {
  yang-version 1;
  namespace "urn:vibe-ports:yang:conformance:choice-duplicate-leaf-in-case-and-shorthand";
  prefix choice-duplicate-leaf-in-case-and-shorthand;
  choice ch { case a { leaf x { type string; } } leaf x { type string; } }
}
