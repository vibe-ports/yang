// SPDX-License-Identifier: BSD-3-Clause
// Hand-written conformance fixture (this repo).
// Schema-mode XPath: a literal or number that does not fit the other operand's type, on either
// side of '=' / '!=', for leaf-lists, enumerations and unions, and libyang's choice of the token
// (the last one of the right operand, the one before the operator on the left).
module must-value-nofit-sides {
  yang-version 1.1;
  namespace "urn:vibe-ports:yang:conformance:must-value-nofit-sides";
  prefix mvns;
  container top {
    leaf n { type uint8; }
    leaf-list ll { type int8; }
    leaf e { type enumeration { enum red; enum green; } }
    leaf u { type union { type uint8; type enumeration { enum big; } } }
    leaf s { type string { length "1..3"; } }
    must "300 = n";
    must "ll != 'x'";
    must "e = 'blue'";
    must "u = 'huge' or u != -1";
    must "s = 'toolong'";
    must "n = 1 + 'x'";
    must "n = 1 and 'abc' = n and e = 'red'";
  }
}
