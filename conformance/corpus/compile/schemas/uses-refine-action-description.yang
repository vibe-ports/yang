// SPDX-License-Identifier: BSD-3-Clause
// Adapted from libyang v5.8.6 tests/utests/schema/test_tree_schema_compile.c:test_uses.
module uses-refine-action-description {
  yang-version 1.1;
  namespace "urn:vibe-ports:yang:conformance:uses-refine-action-description";
  prefix uses-refine-action-description;
  grouping grp { action g { description "super g"; } }
  container top { action e; uses grp { refine g { description "ultra g"; } } }
}
