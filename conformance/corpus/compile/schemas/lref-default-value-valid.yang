// SPDX-License-Identifier: BSD-3-Clause
// Adapted from libyang v5.8.6 tests/utests/schema/test_tree_schema_compile.c:test_type_leafref.
module lref-default-value-valid {
  yang-version 1;
  namespace "urn:vibe-ports:yang:conformance:lref-default-value-valid";
  prefix lref-default-value-valid;
  leaf source { type leafref { path "../target"; } default true; }
  leaf target { type boolean; }
}
