// SPDX-License-Identifier: BSD-3-Clause
// Hand-written conformance fixture (this repo).
module config-under-state {
  yang-version 1.1;
  namespace "urn:vibe-ports:yang:conformance:config-under-state";
  prefix config-under-state;
  container st {
    config false;
    leaf x { type string; config true; }
  }
}
