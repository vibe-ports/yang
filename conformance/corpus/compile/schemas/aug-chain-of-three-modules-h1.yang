// SPDX-License-Identifier: BSD-3-Clause
// Adapted from libyang v5.8.6 tests/utests/schema/test_tree_schema_compile.c:test_augment.
module aug-chain-of-three-modules-h1 {
  yang-version 1;
  namespace "urn:vibe-ports:yang:conformance:aug-chain-of-three-modules-h1";
  prefix aug-chain-of-three-modules-h1;
  typedef atype { type string; } container top { leaf a { type string; } }
}
