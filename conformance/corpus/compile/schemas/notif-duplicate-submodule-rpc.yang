// SPDX-License-Identifier: BSD-3-Clause
// Adapted from libyang v5.8.6 tests/utests/schema/test_tree_schema_compile.c:test_notification.
module notif-duplicate-submodule-rpc {
  yang-version 1.1;
  namespace "urn:vibe-ports:yang:conformance:notif-duplicate-submodule-rpc";
  prefix notif-duplicate-submodule-rpc;
  include notif-duplicate-submodule-rpc-h1;
  notification w;
}
