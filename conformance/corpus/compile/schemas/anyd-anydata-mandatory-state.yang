// SPDX-License-Identifier: BSD-3-Clause
// Adapted from libyang v5.8.6 tests/utests/schema/test_tree_schema_compile.c:test_node_anydata.
module anyd-anydata-mandatory-state {
  yang-version 1.1;
  namespace "urn:vibe-ports:yang:conformance:anyd-anydata-mandatory-state";
  prefix anyd-anydata-mandatory-state;
  anydata any { config false; mandatory true; }
}
