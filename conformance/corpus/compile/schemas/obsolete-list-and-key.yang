// SPDX-License-Identifier: BSD-3-Clause
// Hand-written conformance fixture (this repo).
module obsolete-list-and-key {
  yang-version 1.1;
  namespace "urn:vibe-ports:yang:conformance:obsolete-list-and-key";
  prefix obsolete-list-and-key;
  container c { leaf a { type string; } }
  list l {
    status obsolete;
    key k;
    leaf k { status obsolete; type string; }
    leaf v { type string; }
  }
}
