// SPDX-License-Identifier: BSD-3-Clause
// Adapted from libyang v5.8.6 tests/utests/schema/test_tree_schema_compile.c:test_node_choice.
module choice-case-name-vs-shorthand {
  yang-version 1;
  namespace "urn:vibe-ports:yang:conformance:choice-case-name-vs-shorthand";
  prefix choice-case-name-vs-shorthand;
  choice ch { case a { leaf x { type string; } } leaf a { type string; } }
}
