// SPDX-License-Identifier: BSD-3-Clause
// Hand-written conformance fixture (this repo).
module must-deprecated-node-warning {
  yang-version 1.1;
  namespace "urn:vibe-ports:yang:conformance:must-deprecated-node-warning";
  prefix must-deprecated-node-warning;
  leaf a { status deprecated; type string; }
  leaf b { type string; must "../a = 'x'"; }
}
