// SPDX-License-Identifier: BSD-3-Clause
// Hand-written conformance fixture (this repo).
module grp-shared-a {
  yang-version 1.1;
  namespace "urn:vibe-ports:yang:conformance:grp-shared-a";
  prefix grp-shared-a;
  grouping g {
    leaf x { type string; mandatory true; default "a"; }
  }
}
