// SPDX-License-Identifier: BSD-3-Clause
// Hand-written conformance fixture (this repo).
module bit-all-disabled {
  yang-version 1.1;
  namespace "urn:vibe-ports:yang:conformance:bit-all-disabled";
  prefix bit-all-disabled;
  feature f;
  leaf l { type bits { bit a { if-feature f; } bit b { if-feature f; } } }
}
