// SPDX-License-Identifier: BSD-3-Clause
// Hand-written conformance fixture (this repo).
module ext-annotation-nested {
  yang-version 1.1;
  namespace "urn:vibe-ports:yang:conformance:ext-annotation-nested";
  prefix ext-annotation-nested;
  import ietf-yang-metadata { prefix md; }
  container c {
    md:annotation foo { type string; }
  }
}
