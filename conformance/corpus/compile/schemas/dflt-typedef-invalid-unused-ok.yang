// SPDX-License-Identifier: BSD-3-Clause
// Hand-written conformance fixture (this repo).
module dflt-typedef-invalid-unused-ok {
  yang-version 1.1;
  namespace "urn:vibe-ports:yang:conformance:dflt-typedef-invalid-unused-ok";
  prefix dflt-typedef-invalid-unused-ok;
  typedef t { type uint8 { range 1..10; } default 11; }
  leaf l { type t; default 5; }
}
