// SPDX-License-Identifier: BSD-3-Clause
// Adapted from libyang v5.8.6 tests/utests/schema/test_tree_schema_compile.c:test_augment.
module aug-rpc-input-output-h1 {
  yang-version 1;
  namespace "urn:vibe-ports:yang:conformance:aug-rpc-input-output-h1";
  prefix aug-rpc-input-output-h1;
  container top; rpc func;
}
