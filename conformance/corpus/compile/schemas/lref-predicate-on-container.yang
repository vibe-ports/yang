// SPDX-License-Identifier: BSD-3-Clause
// Adapted from libyang v5.8.6 tests/utests/schema/test_tree_schema_compile.c:test_type_leafref.
module lref-predicate-on-container {
  yang-version 1;
  namespace "urn:vibe-ports:yang:conformance:lref-predicate-on-container";
  prefix lref-predicate-on-container;
  leaf target1 { type string; }
  container a { leaf target2 { type uint8; } }
  leaf ref1 { type leafref { path '/a[target2 = current()/../target1]/target2'; } }
}
