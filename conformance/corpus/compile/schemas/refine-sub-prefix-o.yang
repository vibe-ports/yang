// SPDX-License-Identifier: BSD-3-Clause
// Hand-written conformance fixture (this repo).
module refine-sub-prefix-o {
  yang-version 1.1;
  namespace "urn:vibe-ports:yang:conformance:refine-sub-prefix-o";
  prefix o;
}
