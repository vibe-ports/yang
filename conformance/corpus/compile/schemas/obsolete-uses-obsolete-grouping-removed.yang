// SPDX-License-Identifier: BSD-3-Clause
// Hand-written conformance fixture (this repo).
module obsolete-uses-obsolete-grouping-removed {
  yang-version 1.1;
  namespace "urn:vibe-ports:yang:conformance:obsolete-uses-obsolete-grouping-removed";
  prefix obsolete-uses-obsolete-grouping-removed;
  grouping g { leaf a { type string; } leaf b { type string; status obsolete; } }
  container c { uses g; }
}
