// SPDX-License-Identifier: BSD-3-Clause
// Hand-written conformance fixture (this repo).
module dflt-bits-default-canonicalised {
  yang-version 1.1;
  namespace "urn:vibe-ports:yang:conformance:dflt-bits-default-canonicalised";
  prefix dflt-bits-default-canonicalised;
  leaf l { type bits { bit a; bit b; bit c; } default "c a"; }
}
