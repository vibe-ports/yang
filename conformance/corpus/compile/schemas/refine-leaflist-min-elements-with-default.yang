// SPDX-License-Identifier: BSD-3-Clause
// Adapted from libyang v5.8.6 tests/utests/schema/test_tree_schema_compile.c:test_refine.
module refine-leaflist-min-elements-with-default {
  yang-version 1.1;
  namespace "urn:vibe-ports:yang:conformance:refine-leaflist-min-elements-with-default";
  prefix refine-leaflist-min-elements-with-default;
  import refine-leaflist-min-elements-with-default-h1 { prefix g; }
  uses g:grp { refine c/ll { min-elements 1; } }
}
