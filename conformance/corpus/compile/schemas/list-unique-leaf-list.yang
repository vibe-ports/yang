// SPDX-License-Identifier: BSD-3-Clause
// Adapted from libyang v5.8.6 tests/utests/schema/test_tree_schema_compile.c:test_node_list.
module list-unique-leaf-list {
  yang-version 1;
  namespace "urn:vibe-ports:yang:conformance:list-unique-leaf-list";
  prefix list-unique-leaf-list;
  list l { key x; unique y; leaf x { type string; } leaf-list y { type string; } }
}
