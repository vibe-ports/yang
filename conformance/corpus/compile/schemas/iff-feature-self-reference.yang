// SPDX-License-Identifier: BSD-3-Clause
// Adapted from libyang v5.8.6 tests/utests/schema/test_schema.c:test_feature.
module iff-feature-self-reference {
  yang-version 1.1;
  namespace "urn:vibe-ports:yang:conformance:iff-feature-self-reference";
  prefix iff-feature-self-reference;
  feature f1 { if-feature f1; }
}
