// SPDX-License-Identifier: BSD-3-Clause
// Hand-written conformance fixture (this repo).
module disabled-all-children-disabled-container-kept {
  yang-version 1.1;
  namespace "urn:vibe-ports:yang:conformance:disabled-all-children-disabled-container-kept";
  prefix disabled-all-children-disabled-container-kept;
  feature f;
  container c { leaf a { if-feature f; type string; } }
}
