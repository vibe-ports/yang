module ver-x-refine-dflt-10 {
  yang-version 1;
  namespace "urn:ver:ver-x-refine-dflt-10";
  prefix p;
  import ver-def-11 { prefix d; }
  container c { uses d:g-llist { refine w { default "r"; } } }
}
