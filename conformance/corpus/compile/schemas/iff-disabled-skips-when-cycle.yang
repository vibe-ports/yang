// SPDX-License-Identifier: BSD-3-Clause
// Hand-written conformance fixture (this repo).
module iff-disabled-skips-when-cycle {
  yang-version 1.1;
  namespace "urn:vibe-ports:yang:conformance:iff-disabled-skips-when-cycle";
  prefix iff-disabled-skips-when-cycle;
  feature f;
  container c { if-feature f;
    leaf a { type string; when "../b"; }
    leaf b { type string; when "../a"; } }
}
