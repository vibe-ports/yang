// SPDX-License-Identifier: BSD-3-Clause
// Adapted from libyang v5.8.6 tests/utests/schema/test_tree_schema_compile.c:test_status.
module status-child-deprecated-in-obsolete {
  yang-version 1;
  namespace "urn:vibe-ports:yang:conformance:status-child-deprecated-in-obsolete";
  prefix status-child-deprecated-in-obsolete;
  container c { status obsolete; leaf l { status deprecated; type string; } }
}
