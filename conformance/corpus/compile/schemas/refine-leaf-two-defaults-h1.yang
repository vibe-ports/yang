// SPDX-License-Identifier: BSD-3-Clause
// Adapted from libyang v5.8.6 tests/utests/schema/test_tree_schema_compile.c:test_refine.
module refine-leaf-two-defaults-h1 {
  yang-version 1.1;
  namespace "urn:vibe-ports:yang:conformance:refine-leaf-two-defaults-h1";
  prefix refine-leaf-two-defaults-h1;
  feature f;
  typedef mytype { type string; default "cheers!"; }
  grouping grp {
    container c {
      leaf l { type mytype; default goodbye; }
      leaf-list ll { type mytype; default goodbye; max-elements 6; }
      choice ch { default ca; leaf ca { type int8; } leaf cb { type uint8; } }
      leaf x { type mytype; mandatory true; must 1; }
      anydata a { mandatory false; if-feature f; description original; reference original; }
      container c { config false; leaf l { type string; } }
    } }
}
