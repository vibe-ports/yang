// SPDX-License-Identifier: BSD-3-Clause
// Adapted from libyang v5.8.6 tests/utests/schema/test_tree_schema_compile.c:test_notification.
module notif-in-rpc-via-uses {
  yang-version 1.1;
  namespace "urn:vibe-ports:yang:conformance:notif-in-rpc-via-uses";
  prefix notif-in-rpc-via-uses;
  rpc test { input { container a { uses grp; } } }
  grouping grp { notification invalid { leaf x { type string; } } }
}
