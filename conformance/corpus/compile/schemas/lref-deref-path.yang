// SPDX-License-Identifier: BSD-3-Clause
// Hand-written conformance fixture (this repo).
module lref-deref-path {
  yang-version 1.1;
  namespace "urn:vibe-ports:yang:conformance:lref-deref-path";
  prefix lref-deref-path;
  list l { key k; leaf k { type string; } leaf v { type string; } }
  leaf a { type leafref { path "deref(../b)/../v"; } }
  leaf b { type leafref { path "../l/k"; } }
}
