// SPDX-License-Identifier: BSD-3-Clause
// Hand-written conformance fixture (this repo).
module when-invalid {
  yang-version 1.1;
  namespace "urn:vibe-ports:yang:conformance:when-invalid";
  prefix when-invalid;
  leaf b { when "/nomod:x"; type string; }
}
