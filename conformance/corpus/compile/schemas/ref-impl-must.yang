// SPDX-License-Identifier: BSD-3-Clause
// Hand-written conformance fixture (this repo).
module ref-impl-must {
  yang-version 1.1;
  namespace "urn:vibe-ports:yang:conformance:ref-impl-must";
  prefix rm;
  import ref-impl-target {
    prefix t;
  }
  leaf y {
    type string;
    must "/t:c/t:x = 'a'";
  }
  leaf z {
    when "/t:c";
    type string;
  }
}
