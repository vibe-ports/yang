// SPDX-License-Identifier: BSD-3-Clause
// Hand-written conformance fixture (this repo).
module errpath-unres {
  yang-version 1.1;
  namespace "urn:vibe-ports:yang:conformance:errpath-unres";
  prefix errpath-unres;
  container c {
    leaf r { type leafref { path "../nope"; } }
  }
}
