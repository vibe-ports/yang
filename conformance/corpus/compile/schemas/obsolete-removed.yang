// SPDX-License-Identifier: BSD-3-Clause
// Hand-written conformance fixture (this repo).
module obsolete-removed {
  yang-version 1.1;
  namespace "urn:vibe-ports:yang:conformance:obsolete-removed";
  prefix obsolete-removed;
  container c {
    leaf a { type string; }
    leaf b { status obsolete; type string; }
  }
}
