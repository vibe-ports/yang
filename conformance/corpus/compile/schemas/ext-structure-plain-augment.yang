// SPDX-License-Identifier: BSD-3-Clause
// Hand-written conformance fixture (this repo).
module ext-structure-plain-augment {
  yang-version 1.1;
  namespace "urn:vibe-ports:yang:conformance:ext-structure-plain-augment";
  prefix spa;
  import ext-structure-base { prefix sb; }
  augment "/sb:s/sb:c" {
    leaf y { type string; }
  }
}
