// SPDX-License-Identifier: BSD-2-Clause
// Reduced to the yang-data extension definition; module name, namespace and revision follow
// RFC 8040 (public IETF module). All other content removed.
//
// Copyright (c) 2017 IETF Trust and the persons identified as authors of the code.
// All rights reserved.
//
// Redistribution and use in source and binary forms, with or without modification, is
// permitted pursuant to, and subject to the license terms contained in, the Simplified BSD
// License set forth in Section 4.c of the IETF Trust's Legal Provisions Relating to IETF
// Documents (https://trustee.ietf.org/license-info).
module ietf-restconf {
  yang-version 1.1;
  namespace "urn:ietf:params:xml:ns:yang:ietf-restconf";
  prefix rc;
  revision 2017-01-26;
  extension yang-data { argument name { yin-element true; } description "Reduced from RFC 8040."; }
}
