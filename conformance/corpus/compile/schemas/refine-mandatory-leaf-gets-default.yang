// SPDX-License-Identifier: BSD-3-Clause
// Adapted from libyang v5.8.6 tests/utests/schema/test_tree_schema_compile.c:test_refine.
module refine-mandatory-leaf-gets-default {
  yang-version 1.1;
  namespace "urn:vibe-ports:yang:conformance:refine-mandatory-leaf-gets-default";
  prefix refine-mandatory-leaf-gets-default;
  import refine-mandatory-leaf-gets-default-h1 { prefix g; }
  uses g:grp { refine c/x { default hello; } }
}
