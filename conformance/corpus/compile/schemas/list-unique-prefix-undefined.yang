// SPDX-License-Identifier: BSD-3-Clause
// Adapted from libyang v5.8.6 tests/utests/schema/test_tree_schema_compile.c:test_node_list.
module list-unique-prefix-undefined {
  yang-version 1;
  namespace "urn:vibe-ports:yang:conformance:list-unique-prefix-undefined";
  prefix list-unique-prefix-undefined;
  list l { key x; unique a:x; leaf x { type string; } }
}
