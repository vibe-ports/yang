// SPDX-License-Identifier: BSD-3-Clause
// Hand-written conformance fixture (this repo).
module ref-impl-rc-a {
  yang-version 1.1;
  namespace "urn:vibe-ports:yang:conformance:ref-impl-rc-a";
  prefix a;
  container top;
}
