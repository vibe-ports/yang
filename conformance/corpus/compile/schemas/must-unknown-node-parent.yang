// SPDX-License-Identifier: BSD-3-Clause
// Hand-written conformance fixture (this repo).
// Schema-mode XPath: the "for parent" form of the node-not-found warning, the parent shown as a
// node path, "<config-root>" or "<root>", the excerpt ending at the failing name, and the rest of
// the path with its predicates skipped.
module must-unknown-node-parent {
  yang-version 1.1;
  namespace "urn:vibe-ports:yang:conformance:must-unknown-node-parent";
  prefix munp;
  container c {
    leaf a { type string; }
    container d { leaf e { type string; } }
    must "d/nope = 1";
    must "/nope";
    must "/munp:c/zz and a = 'x'";
    must "d/nope[bad = 1]/also/gone";
    must "d/e[nothere = 1] and ../a";
    must "a | d/nada | d/e";
  }
  container st {
    config false;
    leaf v { type string; }
    must "/nope";
    must "v/leaf = 1";
  }
}
