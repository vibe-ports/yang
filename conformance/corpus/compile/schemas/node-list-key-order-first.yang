// SPDX-License-Identifier: BSD-3-Clause
// Adapted from libyang v5.8.6 tests/utests/schema/test_tree_schema_compile.c:test_node_list.
module node-list-key-order-first {
  yang-version 1.1;
  namespace "urn:vibe-ports:yang:conformance:node-list-key-order-first";
  prefix node-list-key-order-first;
  list l { key "d b c"; leaf a { type string; } leaf b { type string; } leaf c { type string; } leaf d { type string; } }
}
