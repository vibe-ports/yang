// SPDX-License-Identifier: BSD-3-Clause
// Hand-written conformance fixture (this repo).
module ext-yang-data-dup {
  yang-version 1.1;
  namespace "urn:vibe-ports:yang:conformance:ext-yang-data-dup";
  prefix yd;
  import ietf-restconf { prefix rc; }
  container x;
  rc:yang-data t {
    choice c { container x; }
    container x;
  }
}
