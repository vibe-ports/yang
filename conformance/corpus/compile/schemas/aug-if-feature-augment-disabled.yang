// SPDX-License-Identifier: BSD-3-Clause
// Hand-written conformance fixture (this repo).
module aug-if-feature-augment-disabled {
  yang-version 1.1;
  namespace "urn:vibe-ports:yang:conformance:aug-if-feature-augment-disabled";
  prefix aug-if-feature-augment-disabled;
  feature f;
  container root { container cont; }
  augment /root/cont { if-feature f; leaf l { type string; } }
}
