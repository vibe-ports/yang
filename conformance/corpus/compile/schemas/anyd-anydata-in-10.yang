// SPDX-License-Identifier: BSD-3-Clause
// Adapted from libyang v5.8.6 tests/utests/schema/test_tree_schema_compile.c:test_node_anydata.
module anyd-anydata-in-10 {
  yang-version 1;
  namespace "urn:vibe-ports:yang:conformance:anyd-anydata-in-10";
  prefix anyd-anydata-in-10;
  anydata any;
}
