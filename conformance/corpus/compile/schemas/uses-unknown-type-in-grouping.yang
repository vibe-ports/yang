// SPDX-License-Identifier: BSD-3-Clause
// Adapted from libyang v5.8.6 tests/utests/schema/test_tree_schema_compile.c:test_uses.
module uses-unknown-type-in-grouping {
  yang-version 1.1;
  namespace "urn:vibe-ports:yang:conformance:uses-unknown-type-in-grouping";
  prefix uses-unknown-type-in-grouping;
  grouping grp { leaf j { when "1"; type invalid; } }
  container top { uses grp; }
}
