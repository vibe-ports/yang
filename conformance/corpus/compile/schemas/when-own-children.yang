// SPDX-License-Identifier: BSD-3-Clause
// Hand-written conformance fixture (this repo).
module when-own-children {
  yang-version 1.1;
  namespace "urn:vibe-ports:yang:conformance:when-own-children";
  prefix when-own-children;
  container c {
    when "x = 'a'";
    leaf x { type string; }
  }
}
