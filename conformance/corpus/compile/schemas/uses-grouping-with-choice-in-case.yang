// SPDX-License-Identifier: BSD-3-Clause
// Adapted from libyang v5.8.6 tests/utests/schema/test_tree_schema_compile.c:test_uses.
module uses-grouping-with-choice-in-case {
  yang-version 1.1;
  namespace "urn:vibe-ports:yang:conformance:uses-grouping-with-choice-in-case";
  prefix uses-grouping-with-choice-in-case;
  grouping grp { choice gch { case gc1 { leaf y { type string; } } case gc2 { leaf z { type string; } } } }
  choice ch { case one { leaf x { type string; } } case two { uses grp; } }
}
