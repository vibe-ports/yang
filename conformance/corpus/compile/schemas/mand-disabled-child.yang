// SPDX-License-Identifier: BSD-3-Clause
// Hand-written conformance fixture (this repo).
module mand-disabled-child {
  yang-version 1.1;
  namespace "urn:vibe-ports:yang:conformance:mand-disabled-child";
  prefix mand-disabled-child;
  feature f;
  container np {
    leaf m { if-feature f; type string; mandatory true; }
    leaf o { type string; }
  }
}
