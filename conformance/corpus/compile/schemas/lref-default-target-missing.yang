// SPDX-License-Identifier: BSD-3-Clause
// Adapted from libyang v5.8.6 tests/utests/schema/test_tree_schema_compile.c:test_type_leafref.
module lref-default-target-missing {
  yang-version 1;
  namespace "urn:vibe-ports:yang:conformance:lref-default-target-missing";
  prefix lref-default-target-missing;
  leaf source { type leafref { path "../target"; } default true; }
}
