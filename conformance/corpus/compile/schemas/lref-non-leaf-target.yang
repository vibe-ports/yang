// SPDX-License-Identifier: BSD-3-Clause
// Adapted from libyang v5.8.6 tests/utests/schema/test_tree_schema_compile.c:test_type_leafref.
module lref-non-leaf-target {
  yang-version 1;
  namespace "urn:vibe-ports:yang:conformance:lref-non-leaf-target";
  prefix lref-non-leaf-target;
  container a { leaf target2 { type uint8; } }
  leaf ref1 { type leafref { path /a; } }
}
