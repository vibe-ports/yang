// SPDX-License-Identifier: BSD-3-Clause
// Hand-written conformance fixture (this repo).
module ord-z {
  yang-version 1.1;
  namespace "urn:vibe-ports:yang:conformance:ord-z";
  prefix ord-z;
  import ord-base { prefix b; }
  augment /b:c { leaf zz { type string; } }
}
