// SPDX-License-Identifier: BSD-3-Clause
// Hand-written conformance fixture (this repo).
module ext-annotation-no-type {
  yang-version 1.1;
  namespace "urn:vibe-ports:yang:conformance:ext-annotation-no-type";
  prefix ext-annotation-no-type;
  import ietf-yang-metadata { prefix md; }
  md:annotation foo { description "no type"; }
}
