// SPDX-License-Identifier: BSD-3-Clause
// Hand-written conformance fixture (this repo).
module ext-annotation-substmt-order {
  yang-version 1.1;
  namespace "urn:vibe-ports:yang:conformance:ext-annotation-substmt-order";
  prefix ext-annotation-substmt-order;
  import ietf-yang-metadata { prefix md; }
  md:annotation a { type string { length 1; length 2; } status bogus; units u; units v; }
}
