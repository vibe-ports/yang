// SPDX-License-Identifier: BSD-3-Clause
// Adapted from libyang v5.8.6 tests/utests/schema/test_tree_schema_compile.c:test_action.
module rpc-action-augment-output-musts {
  yang-version 1.1;
  namespace "urn:vibe-ports:yang:conformance:rpc-action-augment-output-musts";
  prefix rpc-action-augment-output-musts;
  container top {
    action b { input { leaf x { type int8; } leaf y { type int8; } }
               output { must "result > 25"; must "/top"; leaf result { type int16; } } } }
  augment /top/b/output { leaf result2 { type string; } }
}
