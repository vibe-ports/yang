// SPDX-License-Identifier: BSD-3-Clause
// Hand-written conformance fixture (this repo).
module ref-impl-target {
  yang-version 1.1;
  namespace "urn:vibe-ports:yang:conformance:ref-impl-target";
  prefix t;
  identity base;
  identity one {
    base base;
  }
  container c {
    leaf x {
      type string;
    }
  }
}
