// SPDX-License-Identifier: BSD-3-Clause
// Adapted from libyang v5.8.6 tests/utests/schema/test_tree_schema_compile.c:test_grouping.
module grp-config-lists-from-imported-grouping-h2 {
  yang-version 1;
  namespace "urn:vibe-ports:yang:conformance:grp-config-lists-from-imported-grouping-h2";
  prefix grp-config-lists-from-imported-grouping-h2;
  grouping leafs_group { leaf name { type string; config true; } leaf value { type uint32; config true; } }
}
