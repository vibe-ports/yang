// SPDX-License-Identifier: BSD-3-Clause
// Hand-written conformance fixture (this repo).
module status-main {
  yang-version 1.1;
  namespace "urn:vibe-ports:yang:conformance:status-main";
  prefix status-main;
  include status-sub;
  container c { uses g; }
}
