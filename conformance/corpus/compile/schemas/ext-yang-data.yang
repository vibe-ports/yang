// SPDX-License-Identifier: BSD-3-Clause
// Hand-written conformance fixture (this repo).
module ext-yang-data {
  yang-version 1.1;
  namespace "urn:vibe-ports:yang:conformance:ext-yang-data";
  prefix ext-yang-data;
  import ietf-restconf { prefix rc; }
  rc:yang-data my-data {
    container top { leaf x { type string; } }
  }
}
