// SPDX-License-Identifier: BSD-3-Clause
// Hand-written conformance fixture (this repo).
module ext-augment-structure-nested {
  yang-version 1.1;
  namespace "urn:vibe-ports:yang:conformance:ext-augment-structure-nested";
  prefix asx;
  import ietf-yang-structure-ext { prefix sx; }
  import ext-structure-base { prefix sb; }
  container top {
    sx:augment-structure "/sb:s/sb:c" {
      leaf y { type string; }
    }
  }
}
