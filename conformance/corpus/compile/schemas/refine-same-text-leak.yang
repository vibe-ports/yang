// SPDX-License-Identifier: BSD-3-Clause
// Hand-written conformance fixture (this repo).
module refine-same-text-leak {
  yang-version 1.1;
  namespace "urn:vibe-ports:yang:conformance:refine-same-text-leak";
  prefix refine-same-text-leak;
  grouping inner { leaf x { type string; default "orig-inner"; } }
  grouping outer {
    container k { uses inner { refine x { default "inner-refine"; } } }
    leaf x { type string; default "orig-outer"; }
  }
  container c {
    uses outer { refine x { default "top-refine"; } }
  }
}
