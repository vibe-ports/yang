// SPDX-License-Identifier: BSD-3-Clause
// Hand-written conformance fixture (this repo).
module ext-instance-unknown-extension {
  yang-version 1.1;
  namespace "urn:vibe-ports:yang:conformance:ext-instance-unknown-extension";
  prefix ext-instance-unknown-extension;
  container c { ext-instance-unknown-extension:nosuchext "x"; }
}
