// SPDX-License-Identifier: BSD-3-Clause
// Adapted from libyang v5.8.6 tests/utests/schema/test_tree_schema_compile.c:test_type_leafref.
module lref-disabled-target {
  yang-version 1.1;
  namespace "urn:vibe-ports:yang:conformance:lref-disabled-target";
  prefix lref-disabled-target;
  feature f1;
  leaf ref1 { type leafref { path /target; } }
  leaf target { if-feature 'f1'; type boolean; }
}
