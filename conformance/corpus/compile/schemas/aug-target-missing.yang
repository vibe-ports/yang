// SPDX-License-Identifier: BSD-3-Clause
// Hand-written conformance fixture (this repo).
module aug-target-missing {
  yang-version 1.1;
  namespace "urn:vibe-ports:yang:conformance:aug-target-missing";
  prefix aug-target-missing;
  import aug-base { prefix b; }
  augment /b:nope { leaf m { type string; } }
}
