// SPDX-License-Identifier: BSD-3-Clause
// Hand-written conformance fixture (this repo).
module ext-instance-no-argument {
  yang-version 1.1;
  namespace "urn:vibe-ports:yang:conformance:ext-instance-no-argument";
  prefix ext-instance-no-argument;
  extension e;
  container c { ext-instance-no-argument:e; }
}
