// SPDX-License-Identifier: BSD-3-Clause
// Hand-written conformance fixture (this repo).
module dflt-invalid-for-type {
  yang-version 1.1;
  namespace "urn:vibe-ports:yang:conformance:dflt-invalid-for-type";
  prefix dflt-invalid-for-type;
  leaf l { type uint8; default "abc"; }
}
