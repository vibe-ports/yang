// SPDX-License-Identifier: BSD-3-Clause
// Adapted from libyang v5.8.6 tests/utests/schema/test_tree_schema_compile.c:test_augment.
module aug-notification-via-uses {
  yang-version 1.1;
  namespace "urn:vibe-ports:yang:conformance:aug-notification-via-uses";
  prefix aug-notification-via-uses;
  container root;
  grouping grp { notification grp-notif; }
  augment /root { uses grp; }
}
