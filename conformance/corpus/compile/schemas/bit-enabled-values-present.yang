// SPDX-License-Identifier: BSD-3-Clause
// Hand-written conformance fixture (this repo).
module bit-enabled-values-present {
  yang-version 1.1;
  namespace "urn:vibe-ports:yang:conformance:bit-enabled-values-present";
  prefix bit-enabled-values-present;
  feature f;
  leaf l { type bits { bit a; bit b { if-feature f; } bit c { position 5; } bit d; } }
}
