// SPDX-License-Identifier: BSD-3-Clause
// Hand-written conformance fixture (this repo).
module ext-annotation-import-only {
  yang-version 1.1;
  namespace "urn:vibe-ports:yang:conformance:ext-annotation-import-only";
  prefix ext-annotation-import-only;
  import ietf-yang-metadata { prefix md; }
  md:annotation foo { description "no type"; }
}
