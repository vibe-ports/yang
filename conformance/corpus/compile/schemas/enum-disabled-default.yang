// SPDX-License-Identifier: BSD-3-Clause
// Adapted from libyang v5.8.6 tests/utests/schema/test_schema.c:test_disabled_enum.
module enum-disabled-default {
  yang-version 1.1;
  namespace "urn:vibe-ports:yang:conformance:enum-disabled-default";
  prefix enum-disabled-default;
  feature f;
  leaf l { type enumeration { enum e1 { if-feature f; } enum e2; } default e1; }
}
