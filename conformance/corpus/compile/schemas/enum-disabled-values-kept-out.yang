// SPDX-License-Identifier: BSD-3-Clause
// Adapted from libyang v5.8.6 tests/utests/schema/test_tree_schema_compile.c:test_type_enum.
module enum-disabled-values-kept-out {
  yang-version 1.1;
  namespace "urn:vibe-ports:yang:conformance:enum-disabled-values-kept-out";
  prefix enum-disabled-values-kept-out;
  feature f;
  leaf l { type enumeration { enum automin; enum min { value -2147483648; } enum one { if-feature f; value 1; } enum two; enum seven { value 7; } enum eight; } }
}
