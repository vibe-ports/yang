// SPDX-License-Identifier: BSD-3-Clause
// Hand-written conformance fixture (this repo).
module choice-nested-default-chain {
  yang-version 1.1;
  namespace "urn:vibe-ports:yang:conformance:choice-nested-default-chain";
  prefix choice-nested-default-chain;
  choice outer { default one;
    case one { choice inner { default x; leaf x { type string; } leaf y { type string; } } }
    case two { leaf z { type string; } } }
}
