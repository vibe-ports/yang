// SPDX-License-Identifier: BSD-3-Clause
// Hand-written conformance fixture (this repo).
module enum-disabled-value-auto-assignment-kept {
  yang-version 1.1;
  namespace "urn:vibe-ports:yang:conformance:enum-disabled-value-auto-assignment-kept";
  prefix enum-disabled-value-auto-assignment-kept;
  feature f;
  leaf l { type enumeration { enum a { if-feature f; } enum b; enum c; } }
}
