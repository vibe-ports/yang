// SPDX-License-Identifier: BSD-3-Clause
// Adapted from libyang v5.8.6 tests/utests/schema/test_tree_schema_compile.c:test_augment.
module aug-if-feature-on-augment-and-target {
  yang-version 1.1;
  namespace "urn:vibe-ports:yang:conformance:aug-if-feature-on-augment-and-target";
  prefix aug-if-feature-on-augment-and-target;
  feature f;
  container root { container cont { if-feature f; } }
  augment /root/cont { if-feature f; leaf l { type string; } }
}
