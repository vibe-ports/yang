// SPDX-License-Identifier: BSD-3-Clause
// Hand-written conformance fixture (this repo).
module bit-disabled-default {
  yang-version 1.1;
  namespace "urn:vibe-ports:yang:conformance:bit-disabled-default";
  prefix bit-disabled-default;
  feature f;
  leaf l { type bits { bit a { if-feature f; } bit b; } default "a"; }
}
