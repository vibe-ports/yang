// SPDX-License-Identifier: BSD-3-Clause
// Hand-written conformance fixture (this repo).
module errpath-augment {
  yang-version 1.1;
  namespace "urn:vibe-ports:yang:conformance:errpath-augment";
  prefix errpath-augment;
  import aug-base { prefix b; }
  augment /b:c { leaf x { type no-such-type; } }
}
