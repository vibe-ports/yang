// SPDX-License-Identifier: BSD-3-Clause
// Hand-written conformance fixture (this repo, issue #124).
module uses-augment-empty-nodeid {
  yang-version 1.1;
  namespace "urn:vibe-ports:yang:conformance:uses-augment-empty-nodeid";
  prefix uses-augment-empty-nodeid;
  grouping g { container a; } container c { uses g { augment "" { leaf x { type string; } } } }
}
