// SPDX-License-Identifier: BSD-3-Clause
// Adapted from libyang v5.8.6 tests/utests/schema/test_tree_schema_compile.c:test_node_list.
module list-key-duplicate {
  yang-version 1;
  namespace "urn:vibe-ports:yang:conformance:list-key-duplicate";
  prefix list-key-duplicate;
  list l { key "x y x"; leaf x { type string; } leaf y { type string; } }
}
