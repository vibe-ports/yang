// SPDX-License-Identifier: BSD-3-Clause
// Hand-written conformance fixture (this repo).
module ext-instance-on-augment {
  yang-version 1.1;
  namespace "urn:vibe-ports:yang:conformance:ext-instance-on-augment";
  prefix ext-instance-on-augment;
  extension e { argument arg; }
  container c;
  augment /c { ext-instance-on-augment:e "on-augment"; leaf x { type string; } }
}
