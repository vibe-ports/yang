// SPDX-License-Identifier: BSD-3-Clause
// Adapted from libyang v5.8.6 tests/utests/schema/test_tree_schema_compile.c:test_type_empty.
module dflt-typedef-empty-default {
  yang-version 1;
  namespace "urn:vibe-ports:yang:conformance:dflt-typedef-empty-default";
  prefix dflt-typedef-empty-default;
  typedef mytype { type empty; default x; }
  leaf l { type mytype; }
}
