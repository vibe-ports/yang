// SPDX-License-Identifier: BSD-3-Clause
// Adapted from libyang v5.8.6 tests/utests/schema/test_tree_schema_compile.c:test_action.
module must-action-output-musts {
  yang-version 1.1;
  namespace "urn:vibe-ports:yang:conformance:must-action-output-musts";
  prefix must-action-output-musts;
  container top { action b { input { leaf x { type int8; } } output { must "result > 25"; leaf result { type int16; } } } }
}
