// SPDX-License-Identifier: BSD-3-Clause
// Adapted from libyang v5.8.6 tests/utests/schema/test_tree_schema_compile.c:test_refine.
module refine-default-case-gets-mandatory-child {
  yang-version 1.1;
  namespace "urn:vibe-ports:yang:conformance:refine-default-case-gets-mandatory-child";
  prefix refine-default-case-gets-mandatory-child;
  import refine-default-case-gets-mandatory-child-h1 { prefix g; }
  uses g:grp { refine c/ch/ca/ca { mandatory true; } }
}
