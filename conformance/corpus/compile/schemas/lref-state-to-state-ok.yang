// SPDX-License-Identifier: BSD-3-Clause
// Hand-written conformance fixture (this repo).
module lref-state-to-state-ok {
  yang-version 1.1;
  namespace "urn:vibe-ports:yang:conformance:lref-state-to-state-ok";
  prefix lref-state-to-state-ok;
  leaf ref { config false; type leafref { path /target; } }
  leaf target { config false; type string; }
}
