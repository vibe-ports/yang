// SPDX-License-Identifier: BSD-3-Clause
// Adapted from libyang v5.8.6 tests/utests/schema/test_tree_schema_compile.c:test_node_leaflist.
module node-leaflist-leafref-in-typedef-union {
  yang-version 1;
  namespace "urn:vibe-ports:yang:conformance:node-leaflist-leafref-in-typedef-union";
  prefix node-leaflist-leafref-in-typedef-union;
  typedef mytype { type union { type leafref { path ../target; } type string; } }
  leaf-list ll1 { type union { type decimal64 { fraction-digits 2; } type mytype; } }
  leaf-list ll2 { type leafref { path ../target; } }
  leaf target { type int8; }
}
