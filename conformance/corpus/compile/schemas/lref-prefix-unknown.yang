// SPDX-License-Identifier: BSD-3-Clause
// Adapted from libyang v5.8.6 tests/utests/schema/test_tree_schema_compile.c:test_type_leafref.
module lref-prefix-unknown {
  yang-version 1;
  namespace "urn:vibe-ports:yang:conformance:lref-prefix-unknown";
  prefix lref-prefix-unknown;
  container a { leaf target2 { type uint8; } }
  leaf ref1 { type leafref { path /a:invalid; } }
}
