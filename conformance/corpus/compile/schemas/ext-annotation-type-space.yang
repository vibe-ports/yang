// SPDX-License-Identifier: BSD-3-Clause
// Hand-written conformance fixture (this repo).
module ext-annotation-type-space {
  yang-version 1.1;
  namespace "urn:vibe-ports:yang:conformance:ext-annotation-type-space";
  prefix ext-annotation-type-space;
  import ietf-yang-metadata { prefix md; }
  md:annotation x { type "a b"; }
}
