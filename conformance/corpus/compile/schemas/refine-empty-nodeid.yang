// SPDX-License-Identifier: BSD-3-Clause
// Hand-written conformance fixture (this repo, issue #124).
module refine-empty-nodeid {
  yang-version 1.1;
  namespace "urn:vibe-ports:yang:conformance:refine-empty-nodeid";
  prefix refine-empty-nodeid;
  grouping g { leaf a { type string; } } container c { uses g { refine "" { description "x"; } } }
}
