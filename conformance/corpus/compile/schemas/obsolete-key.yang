// SPDX-License-Identifier: BSD-3-Clause
// Hand-written conformance fixture (this repo).
module obsolete-key {
  yang-version 1.1;
  namespace "urn:vibe-ports:yang:conformance:obsolete-key";
  prefix obsolete-key;
  list l {
    key k;
    leaf k { status obsolete; type string; }
    leaf v { type string; }
  }
}
