// SPDX-License-Identifier: BSD-3-Clause
// Adapted from libyang v5.8.6 tests/utests/schema/test_tree_schema_compile.c:test_action.
module rpc-duplicate-rpc-leaf {
  yang-version 1;
  namespace "urn:vibe-ports:yang:conformance:rpc-duplicate-rpc-leaf";
  prefix rpc-duplicate-rpc-leaf;
  leaf x { type string; }
  rpc x;
}
