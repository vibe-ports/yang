// SPDX-License-Identifier: BSD-3-Clause
// Adapted from libyang v5.8.6 tests/utests/schema/test_tree_schema_compile.c:test_type_dflt.
module dflt-typedef-default-not-inherited-by-union {
  yang-version 1;
  namespace "urn:vibe-ports:yang:conformance:dflt-typedef-default-not-inherited-by-union";
  prefix dflt-typedef-default-not-inherited-by-union;
  typedef mybasetype { type string; default hello; units xxx; }
  leaf l { type union { type decimal64 { fraction-digits 2; } type mybasetype; } }
}
