// SPDX-License-Identifier: BSD-3-Clause
// Adapted from libyang v5.8.6 tests/utests/schema/test_tree_schema_compile.c:test_refine.
module refine-config-true-under-state {
  yang-version 1.1;
  namespace "urn:vibe-ports:yang:conformance:refine-config-true-under-state";
  prefix refine-config-true-under-state;
  import refine-config-true-under-state-h1 { prefix g; }
  uses g:grp { refine c/c/l { config true; } }
}
