// SPDX-License-Identifier: BSD-3-Clause
// Hand-written conformance fixture (this repo).
module ext-annotation-invalid-status {
  yang-version 1.1;
  namespace "urn:vibe-ports:yang:conformance:ext-annotation-invalid-status";
  prefix ext-annotation-invalid-status;
  import ietf-yang-metadata { prefix md; }
  md:annotation a { type string; status bogus; }
}
