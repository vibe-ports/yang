// SPDX-License-Identifier: BSD-3-Clause
// Adapted from libyang v5.8.6 tests/utests/schema/test_tree_schema_compile.c:test_notification.
module notif-duplicate-in-container {
  yang-version 1.1;
  namespace "urn:vibe-ports:yang:conformance:notif-duplicate-in-container";
  prefix notif-duplicate-in-container;
  container c { leaf y { type string; } notification y; }
}
