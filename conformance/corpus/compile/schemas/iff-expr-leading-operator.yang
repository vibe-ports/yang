// SPDX-License-Identifier: BSD-3-Clause
// Adapted from libyang v5.8.6 tests/utests/schema/test_schema.c:test_feature.
module iff-expr-leading-operator {
  yang-version 1.1;
  namespace "urn:vibe-ports:yang:conformance:iff-expr-leading-operator";
  prefix iff-expr-leading-operator;
  feature f1; feature f { if-feature 'and f1'; }
}
