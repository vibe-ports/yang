// SPDX-License-Identifier: BSD-3-Clause
// Adapted from libyang v5.8.6 tests/utests/schema/test_tree_schema_compile.c:test_refine.
module refine-leaf-presence {
  yang-version 1.1;
  namespace "urn:vibe-ports:yang:conformance:refine-leaf-presence";
  prefix refine-leaf-presence;
  import refine-leaf-presence-h1 { prefix g; }
  uses g:grp { refine c/x { presence nonsence; } }
}
