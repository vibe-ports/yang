// SPDX-License-Identifier: BSD-3-Clause
// Adapted from libyang v5.8.6 tests/utests/schema/test_tree_schema_compile.c:test_augment.
module aug-target-if-feature-disabled-no-xpath-warning {
  yang-version 1.1;
  namespace "urn:vibe-ports:yang:conformance:aug-target-if-feature-disabled-no-xpath-warning";
  prefix aug-target-if-feature-disabled-no-xpath-warning;
  import aug-target-if-feature-disabled-no-xpath-warning-h1 { prefix k; }
  augment /k:c { leaf b { type string; } }
  leaf c { when "/k:c/aug-target-if-feature-disabled-no-xpath-warning:b"; type string; }
}
