// SPDX-License-Identifier: BSD-3-Clause
// Adapted from libyang v5.8.6 tests/utests/schema/test_tree_schema_compile.c:test_refine.
module refine-choice-mandatory-true-with-default {
  yang-version 1.1;
  namespace "urn:vibe-ports:yang:conformance:refine-choice-mandatory-true-with-default";
  prefix refine-choice-mandatory-true-with-default;
  import refine-choice-mandatory-true-with-default-h1 { prefix g; }
  uses g:grp { refine c/ch { mandatory true; } }
}
