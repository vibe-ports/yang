// SPDX-License-Identifier: BSD-3-Clause
// Hand-written conformance fixture (this repo).
module disabled-leaf-in-disabled-container-leafref-target {
  yang-version 1.1;
  namespace "urn:vibe-ports:yang:conformance:disabled-leaf-in-disabled-container-leafref-target";
  prefix disabled-leaf-in-disabled-container-leafref-target;
  feature f;
  container c { if-feature f; leaf t { type string; } }
  leaf ref { type leafref { path /c/t; } }
}
