// SPDX-License-Identifier: BSD-3-Clause
// Hand-written conformance fixture (this repo).
module rpc-action-in-list-keyless {
  yang-version 1.1;
  namespace "urn:vibe-ports:yang:conformance:rpc-action-in-list-keyless";
  prefix rpc-action-in-list-keyless;
  list l { config false; leaf v { type string; } action a; }
}
