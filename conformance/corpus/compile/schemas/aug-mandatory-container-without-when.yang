// SPDX-License-Identifier: BSD-3-Clause
// Adapted from libyang v5.8.6 tests/utests/schema/test_tree_schema_compile.c:test_augment.
module aug-mandatory-container-without-when {
  yang-version 1;
  namespace "urn:vibe-ports:yang:conformance:aug-mandatory-container-without-when";
  prefix aug-mandatory-container-without-when;
  import aug-mandatory-container-without-when-h1 { prefix hi; }
  augment /hi:top { container c { leaf d { mandatory true; type int8; } } }
}
