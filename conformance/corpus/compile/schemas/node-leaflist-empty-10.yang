// SPDX-License-Identifier: BSD-3-Clause
// Adapted from libyang v5.8.6 tests/utests/schema/test_tree_schema_compile.c:test_node_leaflist.
module node-leaflist-empty-10 {
  yang-version 1;
  namespace "urn:vibe-ports:yang:conformance:node-leaflist-empty-10";
  prefix node-leaflist-empty-10;
  leaf-list ll { type empty; }
}
