// SPDX-License-Identifier: BSD-3-Clause
// Adapted from libyang v5.8.6 tests/utests/schema/test_tree_schema_compile.c:test_type_leafref.
module lref-predicate-current {
  yang-version 1;
  namespace "urn:vibe-ports:yang:conformance:lref-predicate-current";
  prefix lref-predicate-current;
  list interface { key name; leaf name { type string; } list address { key ip; leaf ip { type string; } } }
  container default-address {
    leaf ifname { type leafref { path "../../interface/name"; } }
    leaf address { type leafref { path "../../interface[  name = current()/../ifname ]/address/ip"; } } }
}
