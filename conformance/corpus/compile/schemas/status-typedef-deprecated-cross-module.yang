// SPDX-License-Identifier: BSD-3-Clause
// Hand-written conformance fixture (this repo).
module status-typedef-deprecated-cross-module {
  yang-version 1.1;
  namespace "urn:vibe-ports:yang:conformance:status-typedef-deprecated-cross-module";
  prefix status-typedef-deprecated-cross-module;
  import status-typedef-deprecated-cross-module-h1 { prefix o; }
  leaf l { type o:t; }
}
