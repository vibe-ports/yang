// SPDX-License-Identifier: BSD-3-Clause
// Adapted from libyang v5.8.6 tests/utests/schema/test_tree_schema_compile.c:test_type_leafref.
module lref-missing-path {
  yang-version 1;
  namespace "urn:vibe-ports:yang:conformance:lref-missing-path";
  prefix lref-missing-path;
  leaf ref1 { type leafref; }
}
