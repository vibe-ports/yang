// SPDX-License-Identifier: BSD-3-Clause
// Adapted from libyang v5.8.6 tests/utests/schema/test_tree_schema_compile.c:test_uses.
module uses-augment-into-grouping-container {
  yang-version 1;
  namespace "urn:vibe-ports:yang:conformance:uses-augment-into-grouping-container";
  prefix uses-augment-into-grouping-container;
  grouping grp { container g; }
  container top { uses grp { augment g { leaf x { type int8; } } } }
}
