// SPDX-License-Identifier: BSD-3-Clause
// Hand-written conformance fixture (this repo).
module notif-in-list-keyless {
  yang-version 1.1;
  namespace "urn:vibe-ports:yang:conformance:notif-in-list-keyless";
  prefix notif-in-list-keyless;
  list l { config false; leaf v { type string; } notification n; }
}
