// SPDX-License-Identifier: BSD-3-Clause
// Hand-written conformance fixture (this repo).
module errpath-submodule-identity {
  yang-version 1.1;
  namespace "urn:vibe-ports:yang:conformance:errpath-submodule-identity";
  prefix errpath-submodule-identity;
  include errpath-sub;
}
