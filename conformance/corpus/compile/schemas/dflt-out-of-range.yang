// SPDX-License-Identifier: BSD-3-Clause
// Hand-written conformance fixture (this repo).
module dflt-out-of-range {
  yang-version 1.1;
  namespace "urn:vibe-ports:yang:conformance:dflt-out-of-range";
  prefix dflt-out-of-range;
  leaf l { type uint8 { range 1..10; } default 11; }
}
