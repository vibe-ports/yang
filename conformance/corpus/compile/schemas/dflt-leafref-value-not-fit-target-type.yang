// SPDX-License-Identifier: BSD-3-Clause
// Adapted from libyang v5.8.6 tests/utests/schema/test_tree_schema_compile.c:test_type_leafref.
module dflt-leafref-value-not-fit-target-type {
  yang-version 1;
  namespace "urn:vibe-ports:yang:conformance:dflt-leafref-value-not-fit-target-type";
  prefix dflt-leafref-value-not-fit-target-type;
  leaf source { type leafref { path "../target"; } default true; }
  leaf target { type uint8; }
}
