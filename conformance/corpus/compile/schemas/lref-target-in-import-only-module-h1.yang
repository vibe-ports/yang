// SPDX-License-Identifier: BSD-3-Clause
// Adapted from libyang v5.8.6 tests/utests/schema/test_tree_schema_compile.c:test_type_leafref.
module lref-target-in-import-only-module-h1 {
  yang-version 1;
  namespace "urn:vibe-ports:yang:conformance:lref-target-in-import-only-module-h1";
  prefix lref-target-in-import-only-module-h1;
  leaf h { type uint16; }
}
