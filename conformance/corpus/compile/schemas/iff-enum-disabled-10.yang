// SPDX-License-Identifier: BSD-3-Clause
// Adapted from libyang v5.8.6 tests/utests/schema/test_tree_schema_compile.c:test_type_enum.
module iff-enum-disabled-10 {
  yang-version 1;
  namespace "urn:vibe-ports:yang:conformance:iff-enum-disabled-10";
  prefix iff-enum-disabled-10;
  feature f; leaf l { type enumeration { enum one { if-feature f; } } }
}
