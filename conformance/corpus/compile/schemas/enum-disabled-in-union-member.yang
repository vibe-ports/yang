// SPDX-License-Identifier: BSD-3-Clause
// Hand-written conformance fixture (this repo).
module enum-disabled-in-union-member {
  yang-version 1.1;
  namespace "urn:vibe-ports:yang:conformance:enum-disabled-in-union-member";
  prefix enum-disabled-in-union-member;
  feature f;
  leaf l { type union { type enumeration { enum a { if-feature f; } enum b; } type int8; } }
}
