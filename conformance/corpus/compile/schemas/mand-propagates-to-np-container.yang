// SPDX-License-Identifier: BSD-3-Clause
// Hand-written conformance fixture (this repo).
module mand-propagates-to-np-container {
  yang-version 1.1;
  namespace "urn:vibe-ports:yang:conformance:mand-propagates-to-np-container";
  prefix mand-propagates-to-np-container;
  container c { container d { leaf m { type string; mandatory true; } } container e { leaf o { type string; } } }
}
