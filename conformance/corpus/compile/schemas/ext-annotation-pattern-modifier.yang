// SPDX-License-Identifier: BSD-3-Clause
// Hand-written conformance fixture (this repo).
module ext-annotation-pattern-modifier {
  yang-version 1.1;
  namespace "urn:vibe-ports:yang:conformance:ext-annotation-pattern-modifier";
  prefix ext-annotation-pattern-modifier;
  import ietf-yang-metadata { prefix md; }
  md:annotation a { type string { pattern "x" { modifier bogus; } } }
}
