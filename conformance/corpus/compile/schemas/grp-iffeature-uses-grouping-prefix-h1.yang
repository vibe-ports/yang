// SPDX-License-Identifier: BSD-3-Clause
// Hand-written conformance fixture (this repo).
module grp-iffeature-uses-grouping-prefix-h1 {
  yang-version 1.1;
  namespace "urn:vibe-ports:yang:conformance:grp-iffeature-uses-grouping-prefix-h1";
  prefix grp-iffeature-uses-grouping-prefix-h1;
  feature f;
  grouping grp { leaf x { if-feature "f"; type string; } leaf y { type string; } }
}
