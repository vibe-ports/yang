// SPDX-License-Identifier: BSD-3-Clause
// Hand-written conformance fixture (this repo).
module status-xmod-a {
  yang-version 1.1;
  namespace "urn:vibe-ports:yang:conformance:status-xmod-a";
  prefix status-xmod-a;
  grouping g { status obsolete; leaf x { type string; } }
}
