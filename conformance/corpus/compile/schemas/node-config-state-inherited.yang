// SPDX-License-Identifier: BSD-3-Clause
// Hand-written conformance fixture (this repo).
module node-config-state-inherited {
  yang-version 1.1;
  namespace "urn:vibe-ports:yang:conformance:node-config-state-inherited";
  prefix node-config-state-inherited;
  container c { config false; container d { leaf l { type string; } leaf-list ll { type string; } list x { key k; leaf k { type string; } } } }
}
