// SPDX-License-Identifier: BSD-3-Clause
// Adapted from libyang v5.8.6 tests/utests/schema/test_tree_schema_compile.c:test_augment.
module aug-chain-of-three-modules-h2 {
  yang-version 1;
  namespace "urn:vibe-ports:yang:conformance:aug-chain-of-three-modules-h2";
  prefix aug-chain-of-three-modules-h2;
  import aug-chain-of-three-modules-h1 { prefix a; } augment /a:top { container c { leaf c { type a:atype; } } }
}
