module ver-reqinst-tpdf-11 {
  yang-version 1.1;
  namespace "urn:ver:ver-reqinst-tpdf-11";
  prefix p;
  typedef r { type leafref { path "/t"; require-instance false; } }
  leaf t { type string; }
  leaf l { type r; }
}
