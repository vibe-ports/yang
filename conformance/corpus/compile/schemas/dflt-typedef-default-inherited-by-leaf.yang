// SPDX-License-Identifier: BSD-3-Clause
// Adapted from libyang v5.8.6 tests/utests/schema/test_tree_schema_compile.c:test_type_dflt.
module dflt-typedef-default-inherited-by-leaf {
  yang-version 1;
  namespace "urn:vibe-ports:yang:conformance:dflt-typedef-default-inherited-by-leaf";
  prefix dflt-typedef-default-inherited-by-leaf;
  typedef mybasetype { type string; default hello; units xxx; }
  leaf l { type mybasetype; }
}
