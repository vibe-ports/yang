// SPDX-License-Identifier: BSD-3-Clause
// Hand-written conformance fixture (this repo).
module ext-annotation-invalid-child {
  yang-version 1.1;
  namespace "urn:vibe-ports:yang:conformance:ext-annotation-invalid-child";
  prefix ext-annotation-invalid-child;
  import ietf-yang-metadata { prefix md; }
  md:annotation a { type string; must "1"; }
}
