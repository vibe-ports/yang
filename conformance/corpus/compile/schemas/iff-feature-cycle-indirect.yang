// SPDX-License-Identifier: BSD-3-Clause
// Adapted from libyang v5.8.6 tests/utests/schema/test_schema.c:test_feature.
module iff-feature-cycle-indirect {
  yang-version 1.1;
  namespace "urn:vibe-ports:yang:conformance:iff-feature-cycle-indirect";
  prefix iff-feature-cycle-indirect;
  feature f1 { if-feature f2; } feature f2 { if-feature f1; }
}
