// SPDX-License-Identifier: BSD-3-Clause
// Hand-written conformance fixture (this repo).
module refine-same-text {
  yang-version 1.1;
  namespace "urn:vibe-ports:yang:conformance:refine-same-text";
  prefix refine-same-text;
  grouping inner { leaf x { type string; default "orig-inner"; } }
  grouping outer {
    leaf x { type string; default "orig-outer"; }
    container k { uses inner { refine x { default "inner-refine"; } } }
  }
  container c {
    uses outer { refine x { default "top-refine"; } }
  }
}
