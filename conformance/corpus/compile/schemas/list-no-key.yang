// SPDX-License-Identifier: BSD-3-Clause
// Adapted from libyang v5.8.6 tests/utests/schema/test_tree_schema_compile.c:test_node_list.
module list-no-key {
  yang-version 1;
  namespace "urn:vibe-ports:yang:conformance:list-no-key";
  prefix list-no-key;
  list l;
}
