// SPDX-License-Identifier: BSD-3-Clause
// Adapted from libyang v5.8.6 tests/utests/schema/test_tree_schema_compile.c:test_node_choice.
module choice-default-case-not-found {
  yang-version 1;
  namespace "urn:vibe-ports:yang:conformance:choice-default-case-not-found";
  prefix choice-default-case-not-found;
  choice ch { default c; case a { leaf x { type string; } } case b { leaf y { type string; } } }
}
