// SPDX-License-Identifier: BSD-3-Clause
// Hand-written conformance fixture (this repo).
module ext-nacm-anyxml {
  yang-version 1.1;
  namespace "urn:vibe-ports:yang:conformance:ext-nacm-anyxml";
  prefix ext-nacm-anyxml;
  import ietf-netconf-acm { prefix nacm; }
  anyxml x { nacm:default-deny-all; }
}
