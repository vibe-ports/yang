// SPDX-License-Identifier: BSD-3-Clause
// Adapted from libyang v5.8.6 tests/utests/schema/test_tree_schema_compile.c:test_when.
module when-uses-in-augment-foreign-prefix-h2 {
  yang-version 1;
  namespace "urn:vibe-ports:yang:conformance:when-uses-in-augment-foreign-prefix-h2";
  prefix when-uses-in-augment-foreign-prefix-h2;
  grouping my-group { leaf my-leaf { type string; } }
}
