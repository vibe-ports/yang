// SPDX-License-Identifier: BSD-3-Clause
// Adapted from libyang v5.8.6 tests/utests/schema/test_tree_schema_compile.c:test_notification.
module notif-in-container-10 {
  yang-version 1;
  namespace "urn:vibe-ports:yang:conformance:notif-in-container-10";
  prefix notif-in-container-10;
  container top { notification x; }
}
