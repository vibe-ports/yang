// SPDX-License-Identifier: BSD-3-Clause
// Adapted from libyang v5.8.6 tests/utests/schema/test_tree_schema_compile.c:test_augment.
module aug-target-rpc-without-input {
  yang-version 1;
  namespace "urn:vibe-ports:yang:conformance:aug-target-rpc-without-input";
  prefix aug-target-rpc-without-input;
  rpc func;
  augment /func { leaf x { type int8; } }
}
