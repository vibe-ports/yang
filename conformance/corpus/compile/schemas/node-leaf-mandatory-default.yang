// SPDX-License-Identifier: BSD-3-Clause
// Hand-written conformance fixture (this repo).
module node-leaf-mandatory-default {
  yang-version 1.1;
  namespace "urn:vibe-ports:yang:conformance:node-leaf-mandatory-default";
  prefix node-leaf-mandatory-default;
  leaf l { type string; mandatory true; default x; }
}
