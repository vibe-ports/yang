// SPDX-License-Identifier: BSD-3-Clause
// Adapted from libyang v5.8.6 tests/utests/schema/test_schema.c:test_feature.
module iff-expr-unexpected-end {
  yang-version 1.1;
  namespace "urn:vibe-ports:yang:conformance:iff-expr-unexpected-end";
  prefix iff-expr-unexpected-end;
  feature f1; feature f2 { if-feature 'f1 and'; }
}
