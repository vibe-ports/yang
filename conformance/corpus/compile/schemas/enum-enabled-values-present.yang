// SPDX-License-Identifier: BSD-3-Clause
// Adapted from libyang v5.8.6 tests/utests/schema/test_tree_schema_compile.c:test_type_enum.
module enum-enabled-values-present {
  yang-version 1.1;
  namespace "urn:vibe-ports:yang:conformance:enum-enabled-values-present";
  prefix enum-enabled-values-present;
  feature f;
  leaf l { type enumeration { enum automin; enum one { if-feature f; value 1; } enum two; } }
}
