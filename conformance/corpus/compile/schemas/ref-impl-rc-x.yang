// SPDX-License-Identifier: BSD-3-Clause
// Hand-written conformance fixture (this repo).
module ref-impl-rc-x {
  yang-version 1.1;
  namespace "urn:vibe-ports:yang:conformance:ref-impl-rc-x";
  prefix x;
  import ref-impl-rc-a {
    prefix a;
  }
  augment "/a:top" {
    leaf ax {
      type string;
    }
  }
  container cx {
    leaf lx {
      type string;
    }
  }
}
