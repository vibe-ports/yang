// SPDX-License-Identifier: BSD-3-Clause
// Hand-written conformance fixture (this repo).
module ext-nacm-twice {
  yang-version 1.1;
  namespace "urn:vibe-ports:yang:conformance:ext-nacm-twice";
  prefix ext-nacm-twice;
  import ietf-netconf-acm { prefix nacm; }
  leaf x {
    nacm:default-deny-write;
    nacm:default-deny-write;
    type string;
  }
}
