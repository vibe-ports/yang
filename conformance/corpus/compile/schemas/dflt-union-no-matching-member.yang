// SPDX-License-Identifier: BSD-3-Clause
// Adapted from libyang v5.8.6 tests/utests/schema/test_tree_schema_compile.c:test_type_union.
module dflt-union-no-matching-member {
  yang-version 1.1;
  namespace "urn:vibe-ports:yang:conformance:dflt-union-no-matching-member";
  prefix dflt-union-no-matching-member;
  leaf target { type int8; }
  leaf l { type union { type leafref { path "/target"; } type int8; } default "999"; }
}
