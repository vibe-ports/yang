// SPDX-License-Identifier: BSD-3-Clause
// Adapted from libyang v5.8.6 tests/utests/schema/test_tree_schema_compile.c:test_augment.
module aug-target-if-feature-disabled-no-xpath-warning-h1 {
  yang-version 1.1;
  namespace "urn:vibe-ports:yang:conformance:aug-target-if-feature-disabled-no-xpath-warning-h1";
  prefix aug-target-if-feature-disabled-no-xpath-warning-h1;
  feature f; container c { if-feature f; leaf a { type string; } }
}
