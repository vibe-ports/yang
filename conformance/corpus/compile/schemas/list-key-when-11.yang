// SPDX-License-Identifier: BSD-3-Clause
// Adapted from libyang v5.8.6 tests/utests/schema/test_tree_schema_compile.c:test_node_list.
module list-key-when-11 {
  yang-version 1.1;
  namespace "urn:vibe-ports:yang:conformance:list-key-when-11";
  prefix list-key-when-11;
  list l { key x; leaf x { type string; when 1; } }
}
