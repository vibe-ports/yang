// SPDX-License-Identifier: BSD-3-Clause
// Hand-written conformance fixture (this repo).
module status-grouping-obsolete-same-module {
  yang-version 1.1;
  namespace "urn:vibe-ports:yang:conformance:status-grouping-obsolete-same-module";
  prefix status-grouping-obsolete-same-module;
  grouping g { status obsolete; leaf x { status obsolete; type string; } }
  container c { uses g; }
}
