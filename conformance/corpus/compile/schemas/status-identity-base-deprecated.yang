// SPDX-License-Identifier: BSD-3-Clause
// Hand-written conformance fixture (this repo).
module status-identity-base-deprecated {
  yang-version 1.1;
  namespace "urn:vibe-ports:yang:conformance:status-identity-base-deprecated";
  prefix status-identity-base-deprecated;
  identity b { status deprecated; }
  identity d { base b; status deprecated; }
}
