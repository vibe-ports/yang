// SPDX-License-Identifier: BSD-3-Clause
// Hand-written conformance fixture (this repo).
module ext-structure-typedef-dup {
  yang-version 1.1;
  namespace "urn:vibe-ports:yang:conformance:ext-structure-typedef-dup";
  prefix std;
  import ietf-yang-structure-ext { prefix sx; }
  sx:structure s {
    container c {
      typedef t { type string; }
      typedef t { type int8; }
      leaf x { type t; }
    }
  }
}
