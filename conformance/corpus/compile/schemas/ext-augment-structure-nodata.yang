// SPDX-License-Identifier: BSD-3-Clause
// Hand-written conformance fixture (this repo).
module ext-augment-structure-nodata {
  yang-version 1.1;
  namespace "urn:vibe-ports:yang:conformance:ext-augment-structure-nodata";
  prefix asn;
  import ietf-yang-structure-ext { prefix sx; }
  import ext-structure-base { prefix sb; }
  sx:augment-structure "/sb:s/sb:c" {
    description "no data-def-stmt";
  }
}
