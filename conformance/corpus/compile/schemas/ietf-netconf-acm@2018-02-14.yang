// SPDX-License-Identifier: BSD-2-Clause
// Reduced to the two extension definitions the libyang NACM plugin keys on; module name,
// namespace and revision follow RFC 8341 (public IETF module). All other content removed.
//
// Copyright (c) 2018 IETF Trust and the persons identified as authors of the code.
// All rights reserved.
//
// Redistribution and use in source and binary forms, with or without modification, is
// permitted pursuant to, and subject to the license terms contained in, the Simplified BSD
// License set forth in Section 4.c of the IETF Trust's Legal Provisions Relating to IETF
// Documents (https://trustee.ietf.org/license-info).
module ietf-netconf-acm {
  yang-version 1.1;
  namespace "urn:ietf:params:xml:ns:yang:ietf-netconf-acm";
  prefix nacm;
  revision 2018-02-14;
  extension default-deny-write { description "Reduced from RFC 8341."; }
  extension default-deny-all { description "Reduced from RFC 8341."; }
}
