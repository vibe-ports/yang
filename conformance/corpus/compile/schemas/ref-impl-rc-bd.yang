// SPDX-License-Identifier: BSD-3-Clause
// Hand-written conformance fixture (this repo).
module ref-impl-rc-bd {
  yang-version 1.1;
  namespace "urn:vibe-ports:yang:conformance:ref-impl-rc-bd";
  prefix bd;
  import ref-impl-rc-xd {
    prefix xd;
  }
  leaf ref {
    type instance-identifier;
    default "/xd:cx/xd:lx";
  }
}
