// SPDX-License-Identifier: BSD-3-Clause
// Hand-written conformance fixture (this repo).
module when-other {
  yang-version 1.1;
  namespace "urn:vibe-ports:yang:conformance:when-other";
  prefix when-other;
  leaf x { type string; }
}
