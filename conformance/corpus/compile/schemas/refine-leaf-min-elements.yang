// SPDX-License-Identifier: BSD-3-Clause
// Adapted from libyang v5.8.6 tests/utests/schema/test_tree_schema_compile.c:test_refine.
module refine-leaf-min-elements {
  yang-version 1.1;
  namespace "urn:vibe-ports:yang:conformance:refine-leaf-min-elements";
  prefix refine-leaf-min-elements;
  import refine-leaf-min-elements-h1 { prefix g; }
  uses g:grp { refine c/x { min-elements 1; } }
}
