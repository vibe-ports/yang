// SPDX-License-Identifier: BSD-3-Clause
// Hand-written conformance fixture (this repo).
module uses-grouping-dup-in-two-uses-same-parent {
  yang-version 1.1;
  namespace "urn:vibe-ports:yang:conformance:uses-grouping-dup-in-two-uses-same-parent";
  prefix uses-grouping-dup-in-two-uses-same-parent;
  grouping g { leaf x { type string; } }
  container c { uses g; uses g; }
}
