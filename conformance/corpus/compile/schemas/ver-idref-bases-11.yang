module ver-idref-bases-11 {
  yang-version 1.1;
  namespace "urn:ver:ver-idref-bases-11";
  prefix p;
  identity a;
  identity b;
  identity c { base a; }
  leaf l { type identityref { base a; base b; } }
}
