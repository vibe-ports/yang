// SPDX-License-Identifier: BSD-3-Clause
// Adapted from libyang v5.8.6 tests/utests/schema/test_schema.c:test_feature.
module iff-feature-expression-enabled-set {
  yang-version 1.1;
  namespace "urn:vibe-ports:yang:conformance:iff-feature-expression-enabled-set";
  prefix iff-feature-expression-enabled-set;
  feature f1; feature f2; feature f3;
  feature orfeature { if-feature "f1 or f2"; }
  feature andfeature { if-feature "f1 and f2"; }
  feature f6 { if-feature "not f1"; }
  feature f7 { if-feature "(f2 and f3) or (not f1)"; }
  leaf x { if-feature orfeature; type string; }
  leaf y { if-feature andfeature; type string; }
}
