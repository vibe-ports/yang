// SPDX-License-Identifier: BSD-3-Clause
// Adapted from libyang v5.8.6 tests/utests/schema/test_tree_schema_compile.c:test_type_leafref.
module lref-too-many-parent-refs {
  yang-version 1;
  namespace "urn:vibe-ports:yang:conformance:lref-too-many-parent-refs";
  prefix lref-too-many-parent-refs;
  container a { leaf target2 { type uint8; } }
  leaf ref1 { type leafref { path ../../toohigh; } }
}
