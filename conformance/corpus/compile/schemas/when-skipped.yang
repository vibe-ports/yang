// SPDX-License-Identifier: BSD-3-Clause
// Hand-written conformance fixture (this repo).
module when-skipped {
  yang-version 1.1;
  namespace "urn:vibe-ports:yang:conformance:when-skipped";
  prefix when-skipped;
  import when-other { prefix o; }
  leaf a { when "/o:x = 'v'"; type string; }
}
