// SPDX-License-Identifier: BSD-3-Clause
// Adapted from libyang v5.8.6 tests/utests/schema/test_tree_schema_compile.c:test_node_list.
module node-list-key-empty-11 {
  yang-version 1.1;
  namespace "urn:vibe-ports:yang:conformance:node-list-key-empty-11";
  prefix node-list-key-empty-11;
  list l { key a; leaf a { type empty; } }
}
