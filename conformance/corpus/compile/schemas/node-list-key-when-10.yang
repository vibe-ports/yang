// SPDX-License-Identifier: BSD-3-Clause
// Adapted from libyang v5.8.6 tests/utests/schema/test_tree_schema_compile.c:test_node_list.
module node-list-key-when-10 {
  yang-version 1;
  namespace "urn:vibe-ports:yang:conformance:node-list-key-when-10";
  prefix node-list-key-when-10;
  feature f;
  list l1 { key "x y"; ordered-by user; leaf y { type string; if-feature f; } leaf x { type string; when 1; } }
  list l2 { config false; leaf value { type string; } }
}
