// SPDX-License-Identifier: BSD-3-Clause
// Hand-written conformance fixture (this repo).
module grp-unused-top-level-invalid {
  yang-version 1.1;
  namespace "urn:vibe-ports:yang:conformance:grp-unused-top-level-invalid";
  prefix grp-unused-top-level-invalid;
  grouping g {
    leaf x { type string; mandatory true; default "a"; }
  }
  container top { leaf y { type string; } }
}
