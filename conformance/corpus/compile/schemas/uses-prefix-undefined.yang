// SPDX-License-Identifier: BSD-3-Clause
// Adapted from libyang v5.8.6 tests/utests/schema/test_tree_schema_compile.c:test_uses.
module uses-prefix-undefined {
  yang-version 1;
  namespace "urn:vibe-ports:yang:conformance:uses-prefix-undefined";
  prefix uses-prefix-undefined;
  uses a:missingprefix;
}
