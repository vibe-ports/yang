// SPDX-License-Identifier: BSD-3-Clause
// Hand-written conformance fixture (this repo, issue #124).
module aug-blank-nodeid {
  yang-version 1.1;
  namespace "urn:vibe-ports:yang:conformance:aug-blank-nodeid";
  prefix aug-blank-nodeid;
  container c; augment " " { leaf x { type string; } }
}
