// SPDX-License-Identifier: BSD-3-Clause
// Adapted from libyang v5.8.6 tests/utests/schema/test_tree_schema_compile.c:test_uses.
module uses-duplicate-leaf-defined-after {
  yang-version 1;
  namespace "urn:vibe-ports:yang:conformance:uses-duplicate-leaf-defined-after";
  prefix uses-duplicate-leaf-defined-after;
  grouping grp { leaf m { type string; } }
  uses grp;
  leaf m { type int8; }
}
