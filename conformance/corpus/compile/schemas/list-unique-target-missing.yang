// SPDX-License-Identifier: BSD-3-Clause
// Adapted from libyang v5.8.6 tests/utests/schema/test_tree_schema_compile.c:test_node_list.
module list-unique-target-missing {
  yang-version 1;
  namespace "urn:vibe-ports:yang:conformance:list-unique-target-missing";
  prefix list-unique-target-missing;
  list l { key x; unique c/x; leaf x { type string; } container c { leaf y { type string; } } }
}
