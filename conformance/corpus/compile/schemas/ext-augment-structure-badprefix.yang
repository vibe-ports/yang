// SPDX-License-Identifier: BSD-3-Clause
// Hand-written conformance fixture (this repo).
module ext-augment-structure-badprefix {
  yang-version 1.1;
  namespace "urn:vibe-ports:yang:conformance:ext-augment-structure-badprefix";
  prefix asb;
  import ietf-yang-structure-ext { prefix sx; }
  import ext-structure-base { prefix sb; }
  sx:augment-structure "/xx:s/sb:c" {
    leaf y { type string; }
  }
}
