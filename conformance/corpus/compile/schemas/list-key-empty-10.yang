// SPDX-License-Identifier: BSD-3-Clause
// Adapted from libyang v5.8.6 tests/utests/schema/test_tree_schema_compile.c:test_node_list.
module list-key-empty-10 {
  yang-version 1;
  namespace "urn:vibe-ports:yang:conformance:list-key-empty-10";
  prefix list-key-empty-10;
  list l { key x; leaf x { type empty; } }
}
