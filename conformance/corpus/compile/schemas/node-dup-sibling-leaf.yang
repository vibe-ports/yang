// SPDX-License-Identifier: BSD-3-Clause
// Hand-written conformance fixture (this repo).
module node-dup-sibling-leaf {
  yang-version 1.1;
  namespace "urn:vibe-ports:yang:conformance:node-dup-sibling-leaf";
  prefix node-dup-sibling-leaf;
  container c { leaf a { type string; } leaf a { type int8; } }
}
