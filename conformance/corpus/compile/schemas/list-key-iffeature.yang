// SPDX-License-Identifier: BSD-3-Clause
// Hand-written conformance fixture (this repo).
module list-key-iffeature {
  yang-version 1.1;
  namespace "urn:vibe-ports:yang:conformance:list-key-iffeature";
  prefix list-key-iffeature;
  feature f;
  list l {
    key k;
    leaf k { if-feature f; type string; }
    leaf v { type string; }
  }
}
