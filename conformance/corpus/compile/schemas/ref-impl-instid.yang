// SPDX-License-Identifier: BSD-3-Clause
// Hand-written conformance fixture (this repo).
module ref-impl-instid {
  yang-version 1.1;
  namespace "urn:vibe-ports:yang:conformance:ref-impl-instid";
  prefix rn;
  import ref-impl-target {
    prefix t;
  }
  leaf ref {
    type instance-identifier;
    default "/t:c/t:x";
  }
}
