// SPDX-License-Identifier: BSD-3-Clause
// Hand-written conformance fixture (this repo).
module node-dup-top-level-leaf-container {
  yang-version 1.1;
  namespace "urn:vibe-ports:yang:conformance:node-dup-top-level-leaf-container";
  prefix node-dup-top-level-leaf-container;
  leaf x { type string; }
  container x;
}
