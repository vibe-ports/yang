// SPDX-License-Identifier: BSD-3-Clause
// Adapted from libyang v5.8.6 tests/utests/schema/test_tree_schema_compile.c:test_node_choice.
module choice-default-case-wrong-module-h1 {
  yang-version 1;
  namespace "urn:vibe-ports:yang:conformance:choice-default-case-wrong-module-h1";
  prefix choice-default-case-wrong-module-h1;
  leaf z { type string; }
}
