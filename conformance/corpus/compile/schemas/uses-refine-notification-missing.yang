// SPDX-License-Identifier: BSD-3-Clause
// Adapted from libyang v5.8.6 tests/utests/schema/test_tree_schema_compile.c:test_uses.
module uses-refine-notification-missing {
  yang-version 1.1;
  namespace "urn:vibe-ports:yang:conformance:uses-refine-notification-missing";
  prefix uses-refine-notification-missing;
  grouping grp { notification g { description "super g"; } }
  container top { notification h; uses grp { refine h { description "ultra h"; } } }
}
