// SPDX-License-Identifier: BSD-3-Clause
// Adapted from libyang v5.8.6 tests/utests/schema/test_tree_schema_compile.c:test_type_leafref.
module lref-disabled-ref-target-missing {
  yang-version 1.1;
  namespace "urn:vibe-ports:yang:conformance:lref-disabled-ref-target-missing";
  prefix lref-disabled-ref-target-missing;
  feature f1;
  leaf ref1 { if-feature 'f1'; type leafref { path /target; } }
}
