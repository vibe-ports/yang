// SPDX-License-Identifier: BSD-3-Clause
// Adapted from libyang v5.8.6 tests/utests/schema/test_tree_schema_compile.c:test_type_dflt.
module mand-leaf-with-typedef-default-ignored {
  yang-version 1.1;
  namespace "urn:vibe-ports:yang:conformance:mand-leaf-with-typedef-default-ignored";
  prefix mand-leaf-with-typedef-default-ignored;
  typedef t { type string; default dflt; }
  leaf m { type t; mandatory true; }
}
