// SPDX-License-Identifier: BSD-3-Clause
// Hand-written conformance fixture (this repo).
module ord-base {
  yang-version 1.1;
  namespace "urn:vibe-ports:yang:conformance:ord-base";
  prefix ord-base;
  container c { leaf own { type string; } }
}
