// SPDX-License-Identifier: BSD-3-Clause
// Adapted from libyang v5.8.6 tests/utests/schema/test_tree_schema_compile.c:test_action.
module rpc-action-in-rpc-via-augment {
  yang-version 1.1;
  namespace "urn:vibe-ports:yang:conformance:rpc-action-in-rpc-via-augment";
  prefix rpc-action-in-rpc-via-augment;
  rpc test { input { container a { leaf b { type string; } } } }
  augment /test/input/a { action invalid { input { leaf x { type string; } } } }
}
