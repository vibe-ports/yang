// SPDX-License-Identifier: BSD-3-Clause
// Adapted from libyang v5.8.6 tests/utests/schema/test_tree_schema_compile.c:test_node_leaflist.
module node-leaflist-empty-default {
  yang-version 1.1;
  namespace "urn:vibe-ports:yang:conformance:node-leaflist-empty-default";
  prefix node-leaflist-empty-default;
  leaf-list ll { type empty; default x; }
}
