// SPDX-License-Identifier: BSD-3-Clause
// Hand-written conformance fixture (this repo).
module ext-annotation-user {
  yang-version 1.1;
  namespace "urn:vibe-ports:yang:conformance:ext-annotation-user";
  prefix ext-annotation-user;
  import ext-annotation-import-only { prefix i; }
  leaf x { type string; }
}
