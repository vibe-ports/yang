module ver-idref-bases-10 {
  yang-version 1;
  namespace "urn:ver:ver-idref-bases-10";
  prefix p;
  identity a;
  identity b;
  identity c { base a; }
  leaf l { type identityref { base a; base b; } }
}
