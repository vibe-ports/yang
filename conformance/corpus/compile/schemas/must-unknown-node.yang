// SPDX-License-Identifier: BSD-3-Clause
// Hand-written conformance fixture (this repo).
module must-unknown-node {
  yang-version 1.1;
  namespace "urn:vibe-ports:yang:conformance:must-unknown-node";
  prefix must-unknown-node;
  container c {
    leaf a { type string; }
    must "nope = 1";
  }
}
