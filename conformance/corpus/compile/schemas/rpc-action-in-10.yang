// SPDX-License-Identifier: BSD-3-Clause
// Adapted from libyang v5.8.6 tests/utests/schema/test_tree_schema_compile.c:test_action.
module rpc-action-in-10 {
  yang-version 1;
  namespace "urn:vibe-ports:yang:conformance:rpc-action-in-10";
  prefix rpc-action-in-10;
  container top { action x; }
}
