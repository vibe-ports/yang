// SPDX-License-Identifier: BSD-3-Clause
// Adapted from libyang v5.8.6 tests/utests/schema/test_tree_schema_compile.c:test_action.
module rpc-duplicate-action-action {
  yang-version 1.1;
  namespace "urn:vibe-ports:yang:conformance:rpc-duplicate-action-action";
  prefix rpc-duplicate-action-action;
  container c { action z; action z; }
}
