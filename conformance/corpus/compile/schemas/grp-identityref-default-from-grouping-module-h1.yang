// SPDX-License-Identifier: BSD-3-Clause
// Adapted from libyang v5.8.6 tests/utests/schema/test_tree_schema_compile.c:test_grouping.
module grp-identityref-default-from-grouping-module-h1 {
  yang-version 1;
  namespace "urn:vibe-ports:yang:conformance:grp-identityref-default-from-grouping-module-h1";
  prefix grp-identityref-default-from-grouping-module-h1;
  identity base_identity;
  identity id1 { base "base_identity"; }
  grouping attrs_group { leaf name { type identityref { base "base_identity"; } default "id1"; } }
}
