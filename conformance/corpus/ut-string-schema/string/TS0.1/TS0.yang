module TS0 {
  yang-version 1.1;
  namespace "urn:tests:TS0";
  prefix pref;
typedef my_type {    type string {length "10 .. 20 | 50 .. 100 | 255";}}leaf port {type my_type {length "min .. 15 | max";}}}
