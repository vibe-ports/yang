module TPATTERN_2 {
  yang-version 1.1;
  namespace "urn:tests:TPATTERN_2";
  prefix pref;
typedef my_type {   type string{       pattern '[a-zA-Z_][a-zA-Z0-9\-_.]*' ;       pattern 'abc.*' {modifier invert-match;}}}leaf port {type my_type {pattern 'bcd.*';}}}
