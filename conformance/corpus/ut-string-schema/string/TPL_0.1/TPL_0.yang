module TPL_0 {
  yang-version 1.1;
  namespace "urn:tests:TPL_0";
  prefix pref;
typedef my_type {   type string{       length  "2 .. 10";   }}leaf port {type my_type{ pattern "[a-zA-Z_][a-zA-Z0-9\\-_.]*";}}}
