module schema2 {
  yang-version 1.1;
  namespace "urn:tests:schema2";
  prefix s2;

  container a {
    container b {
      leaf c {
        type string;
        default "dflt";
      }
      list l {
        key "k";
        leaf k {
          type string;
        }
      }
      list l2 {
        key "k2";
        leaf k2 {
          type string;
        }
      }
    }
    leaf-list ll {
      type string;
    }
  }
  list tl {
    key "tk";
    leaf tk {
      type string;
    }
  }
}
