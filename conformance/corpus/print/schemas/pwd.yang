module pwd {
  yang-version 1.1;
  namespace "urn:vibe-ports:pwd";
  prefix pwd;

  description "With-defaults printing with state defaults: the schema of data/print_wd_test.go (wdFixture).";

  container c {
    leaf a { type string; default "da"; }
    leaf b { type uint8; default "5"; }
    leaf-list ll { type string; default "x"; default "y"; }
    leaf-list ll2 { type uint8; }
    leaf none { type string; }
    container np { leaf d { type string; default "dd"; } }
    container np2 {
      leaf e { type string; default "ee"; }
      leaf f { type string; }
    }
    container pres {
      presence "p";
      leaf g { type string; default "gg"; }
    }
    list l {
      key k;
      leaf k { type string; }
      leaf v { type string; default "vv"; }
    }
    leaf st { config false; type string; default "sd"; }
    container stc {
      config false;
      leaf s2 { type string; default "s2d"; }
    }
  }
}
