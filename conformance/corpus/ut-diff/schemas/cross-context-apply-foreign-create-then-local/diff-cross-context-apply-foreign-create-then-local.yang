// SPDX-License-Identifier: BSD-3-Clause
// Hand-written conformance fixture (this repo).
module diff-cross-context-apply-foreign-create-then-local {
  yang-version 1.1;
  namespace "urn:vibe-ports:yang:diff-cross-context-apply-foreign-create-then-local";
  prefix dccafctl;

  leaf z { type string; }
  leaf x { type string; }
}
