// SPDX-License-Identifier: BSD-3-Clause
// Deterministically generated conformance fixture (this repo).
module diff-sweep-37 {
  yang-version 1.1;
  namespace "urn:vibe-ports:yang:ut-diff:sweep:37";
  prefix ds37;

  container top {
    leaf-list c0 { type string; ordered-by user; }
    leaf-list c1 { type string; ordered-by system; }
    leaf-list c2 { type int16; ordered-by system; }
    leaf-list c3 { type string; ordered-by user; }
    list c4 {
      key "key";
      leaf key { type string; }
      leaf value { type string; }
    }
  }
}
