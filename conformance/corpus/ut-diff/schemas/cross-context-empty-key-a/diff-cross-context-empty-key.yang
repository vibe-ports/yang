// SPDX-License-Identifier: BSD-3-Clause
// Hand-written conformance fixture (this repo).
module diff-cross-context-empty-key {
  yang-version 1.1;
  namespace "urn:vibe-ports:yang:diff-cross-context-empty-key";
  prefix dcek;

  list l {
    key "a";
    leaf a { type string; }
  }
}
