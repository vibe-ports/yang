// SPDX-License-Identifier: BSD-3-Clause
// Deterministically generated conformance fixture (this repo).
module diff-sweep-18 {
  yang-version 1.1;
  namespace "urn:vibe-ports:yang:ut-diff:sweep:18";
  prefix ds18;

  container top {
    leaf c0 { type string; }
    leaf-list c1 { type string; ordered-by user; }
    leaf c2 { type string; }
    list c3 {
      key "key";
      leaf key { type string; }
      leaf value { type string; }
    }
  }
}
