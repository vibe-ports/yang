// SPDX-License-Identifier: BSD-3-Clause
// Deterministically generated conformance fixture (this repo).
module diff-sweep-21 {
  yang-version 1.1;
  namespace "urn:vibe-ports:yang:ut-diff:sweep:21";
  prefix ds21;

  container top {
    leaf-list c0 { type string; ordered-by system; }
    leaf-list c1 { type int8; ordered-by system; }
    leaf c2 { type string; }
    leaf c3 { type string; }
  }
}
