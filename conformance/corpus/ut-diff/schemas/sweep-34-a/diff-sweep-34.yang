// SPDX-License-Identifier: BSD-3-Clause
// Deterministically generated conformance fixture (this repo).
module diff-sweep-34 {
  yang-version 1.1;
  namespace "urn:vibe-ports:yang:ut-diff:sweep:34";
  prefix ds34;

  container top {
    list c0 {
      key "key";
      leaf key { type string; }
      leaf value { type string; }
    }
    leaf-list c1 { type string; ordered-by system; }
    leaf c2 { type string; }
    leaf-list c3 { type int16; ordered-by system; }
    leaf-list c4 { type string; ordered-by user; }
  }
}
