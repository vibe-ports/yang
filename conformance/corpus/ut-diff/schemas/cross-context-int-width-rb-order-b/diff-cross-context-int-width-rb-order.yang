// SPDX-License-Identifier: BSD-3-Clause
// Hand-written conformance fixture (this repo).
module diff-cross-context-int-width-rb-order {
  yang-version 1.1;
  namespace "urn:vibe-ports:yang:diff-cross-context-int-width-rb-order";
  prefix dcciwrbo;

  container top {
    presence "retain";
    leaf-list v {
      type int8;
    }
  }
}
