// SPDX-License-Identifier: BSD-3-Clause
// Deterministically generated conformance fixture (this repo).
module diff-sweep-06 {
  yang-version 1.1;
  namespace "urn:vibe-ports:yang:ut-diff:sweep:06";
  prefix ds06;

  container top {
    list c0 {
      key "key";
      leaf key { type string; }
      leaf value { type string; }
    }
    leaf-list c1 { type string; ordered-by system; }
    leaf-list c2 { type string; ordered-by user; }
    leaf-list c3 { type string; ordered-by user; }
    leaf c4 { type string; }
  }
}
