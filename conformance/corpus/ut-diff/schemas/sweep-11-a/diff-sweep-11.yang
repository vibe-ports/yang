// SPDX-License-Identifier: BSD-3-Clause
// Deterministically generated conformance fixture (this repo).
module diff-sweep-11 {
  yang-version 1.1;
  namespace "urn:vibe-ports:yang:ut-diff:sweep:11";
  prefix ds11;

  container top {
    leaf-list c0 { type int8; ordered-by system; }
    leaf-list c1 { type string; ordered-by user; }
    list c2 {
      key "key";
      leaf key { type string; }
      leaf value { type string; }
    }
    leaf-list c3 { type string; ordered-by user; }
    leaf-list c4 { type string; ordered-by system; }
  }
}
