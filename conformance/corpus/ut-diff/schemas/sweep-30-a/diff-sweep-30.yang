// SPDX-License-Identifier: BSD-3-Clause
// Deterministically generated conformance fixture (this repo).
module diff-sweep-30 {
  yang-version 1.1;
  namespace "urn:vibe-ports:yang:ut-diff:sweep:30";
  prefix ds30;

  container top {
    list c0 {
      key "key";
      leaf key { type string; }
      leaf value { type string; }
    }
    leaf-list c1 { type int16; ordered-by system; }
    leaf-list c2 { type int16; ordered-by system; }
    leaf-list c3 { type int8; ordered-by system; }
  }
}
