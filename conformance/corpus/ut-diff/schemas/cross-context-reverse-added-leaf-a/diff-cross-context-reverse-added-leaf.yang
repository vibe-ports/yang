// SPDX-License-Identifier: BSD-3-Clause
// Hand-written conformance fixture (this repo).
module diff-cross-context-reverse-added-leaf {
  yang-version 1.1;
  namespace "urn:vibe-ports:yang:diff-cross-context-reverse-added-leaf";
  prefix dccral;

  container top {
    leaf x { type string; }
    leaf b { type string; }
  }
}
