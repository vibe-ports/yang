// SPDX-License-Identifier: BSD-3-Clause
// Hand-written conformance fixture (this repo).
module diff-cross-context-foreign-creates-hashed {
  yang-version 1.1;
  namespace "urn:vibe-ports:yang:diff-cross-context-foreign-creates-hashed";
  prefix dccfch;

  container top {
    leaf a { type string; }
    leaf b { type string; }
    leaf c { type string; }
    leaf d { type string; }
    leaf e { type string; }
  }
}
