// SPDX-License-Identifier: BSD-3-Clause
// Deterministically generated conformance fixture (this repo).
module diff-sweep-15 {
  yang-version 1.1;
  namespace "urn:vibe-ports:yang:ut-diff:sweep:15";
  prefix ds15;

  container top {
    leaf-list c0 { type string; ordered-by user; }
    leaf-list c1 { type string; ordered-by system; }
    leaf c2 { type string; }
  }
}
