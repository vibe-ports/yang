// SPDX-License-Identifier: BSD-3-Clause
// Deterministically generated conformance fixture (this repo).
module diff-sweep-23 {
  yang-version 1.1;
  namespace "urn:vibe-ports:yang:ut-diff:sweep:23";
  prefix ds23;

  container top {
    leaf c0 { type string; }
    leaf-list c1 { type string; ordered-by user; }
    leaf-list c2 { type string; ordered-by system; }
    leaf-list c3 { type int8; ordered-by system; }
  }
}
