// SPDX-License-Identifier: BSD-3-Clause
// Deterministically generated conformance fixture (this repo).
module diff-sweep-28 {
  yang-version 1.1;
  namespace "urn:vibe-ports:yang:ut-diff:sweep:28";
  prefix ds28;

  container top {
    list c0 {
      key "key";
      leaf key { type string; }
      leaf value { type string; }
    }
    leaf c1 { type string; }
    list c2 {
      key "key";
      leaf key { type string; }
      leaf value { type string; }
    }
    leaf-list c3 { type int8; ordered-by system; }
    leaf-list c4 { type int16; ordered-by system; }
  }
}
