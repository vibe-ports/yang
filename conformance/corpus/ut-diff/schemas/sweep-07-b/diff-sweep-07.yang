// SPDX-License-Identifier: BSD-3-Clause
// Deterministically generated conformance fixture (this repo).
module diff-sweep-07 {
  yang-version 1.1;
  namespace "urn:vibe-ports:yang:ut-diff:sweep:07";
  prefix ds07;

  container top {
    leaf-list c0 { type string; ordered-by user; }
    list c1 {
      key "key";
      leaf key { type string; }
      leaf value { type string; }
    }
    leaf-list c2 { type string; ordered-by user; }
    leaf-list c3 { type string; ordered-by system; }
    leaf-list c4 { type string; ordered-by user; }
  }
}
