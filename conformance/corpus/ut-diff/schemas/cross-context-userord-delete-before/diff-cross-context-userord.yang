// SPDX-License-Identifier: BSD-3-Clause
// Hand-written conformance fixture (this repo).
module diff-cross-context-userord {
  yang-version 1.1;
  namespace "urn:vibe-ports:yang:cross-context-userord-delete-before";
  prefix dccu;

  leaf-list v {
    ordered-by user;
    type string;
  }
}
