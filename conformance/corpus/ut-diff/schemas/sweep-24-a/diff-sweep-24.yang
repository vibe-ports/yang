// SPDX-License-Identifier: BSD-3-Clause
// Deterministically generated conformance fixture (this repo).
module diff-sweep-24 {
  yang-version 1.1;
  namespace "urn:vibe-ports:yang:ut-diff:sweep:24";
  prefix ds24;

  container top {
    leaf-list c0 { type int16; ordered-by system; }
    leaf c1 { type string; }
    leaf-list c2 { type int8; ordered-by system; }
    leaf c3 { type string; }
    leaf-list c4 { type string; ordered-by system; }
  }
}
