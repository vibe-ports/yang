// SPDX-License-Identifier: BSD-3-Clause
// Hand-written conformance fixture (this repo).
module diff-cross-context-foreign-creates {
  yang-version 1.1;
  namespace "urn:vibe-ports:yang:diff-cross-context-foreign-creates";
  prefix dccfc;

  container top {
    leaf a { type string; }
    leaf b { type string; }
    leaf c { type string; }
    leaf d { type string; }
  }
}
