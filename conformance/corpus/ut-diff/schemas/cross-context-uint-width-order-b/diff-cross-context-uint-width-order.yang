// SPDX-License-Identifier: BSD-3-Clause
// Hand-written conformance fixture (this repo).
module diff-cross-context-uint-width-order {
  yang-version 1.1;
  namespace "urn:vibe-ports:yang:diff-cross-context-uint-width-order";
  prefix dccuwo;

  container top {
    leaf-list v { type uint32; }
  }
}
