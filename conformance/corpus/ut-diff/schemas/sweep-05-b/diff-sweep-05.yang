// SPDX-License-Identifier: BSD-3-Clause
// Deterministically generated conformance fixture (this repo).
module diff-sweep-05 {
  yang-version 1.1;
  namespace "urn:vibe-ports:yang:ut-diff:sweep:05";
  prefix ds05;

  container top {
    leaf c0 { type string; }
    leaf-list c1 { type int8; ordered-by system; }
    list c2 {
      key "key";
      leaf key { type string; }
      leaf value { type string; }
    }
    leaf-list c3 { type int16; ordered-by system; }
    leaf-list c4 { type int8; ordered-by system; }
  }
}
