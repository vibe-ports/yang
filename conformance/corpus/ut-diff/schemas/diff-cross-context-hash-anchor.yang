// SPDX-License-Identifier: BSD-3-Clause

module diff-cross-context-hash-anchor {
  yang-version 1.1;
  namespace "urn:vibe-ports:yang:diff-cross-context-hash-anchor";
  prefix dccha;

  container t {
    leaf a { type string; }
    leaf b { type string; }
    leaf c { type string; }
    leaf d { type string; }
    leaf e { type string; }
  }
}
