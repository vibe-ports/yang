// SPDX-License-Identifier: BSD-3-Clause
// Deterministically generated conformance fixture (this repo).
module diff-sweep-38 {
  yang-version 1.1;
  namespace "urn:vibe-ports:yang:ut-diff:sweep:38";
  prefix ds38;

  container top {
    leaf-list c0 { type string; ordered-by system; }
    leaf-list c1 { type int8; ordered-by system; }
    leaf-list c2 { type int16; ordered-by system; }
    list c3 {
      key "key";
      leaf key { type string; }
      leaf value { type string; }
    }
    leaf-list c4 { type string; ordered-by system; }
  }
}
