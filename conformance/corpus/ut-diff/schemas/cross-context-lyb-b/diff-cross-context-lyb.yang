// SPDX-License-Identifier: BSD-3-Clause
// Hand-written conformance fixture (this repo).
module diff-cross-context-lyb {
  yang-version 1.1;
  namespace "urn:vibe-ports:yang:diff-cross-context-lyb";
  prefix dccl;

  container top {
    leaf-list address { type string; }
    leaf-list enum-value {
      type enumeration {
        enum same { value 1; }
        enum high { value 255; }
      }
    }
    leaf-list enum-negative {
      type enumeration {
        enum same { value 1; }
        enum other { value -1; }
      }
    }
    leaf-list bits-value {
      type bits {
        bit same { position 0; }
        bit high { position 7; }
      }
    }
  }
}
