// SPDX-License-Identifier: BSD-3-Clause
// Hand-written conformance fixture (this repo).
module diff-cross-context-singleton-leaflist {
  yang-version 1.1;
  namespace "urn:vibe-ports:yang:diff-cross-context-singleton-leaflist";
  prefix dcsl;

  container top {
    presence "retain top";
    leaf a { type string; }
    leaf-list b {
      type string;
      ordered-by system;
    }
  }
}
