// SPDX-License-Identifier: BSD-3-Clause
// Deterministically generated conformance fixture (this repo).
module diff-sweep-19 {
  yang-version 1.1;
  namespace "urn:vibe-ports:yang:ut-diff:sweep:19";
  prefix ds19;

  container top {
    leaf-list c0 { type int16; ordered-by system; }
    list c1 {
      key "key";
      leaf key { type string; }
      leaf value { type string; }
    }
    leaf-list c2 { type string; ordered-by system; }
    leaf-list c3 { type int8; ordered-by system; }
  }
}
