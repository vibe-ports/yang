// SPDX-License-Identifier: BSD-3-Clause
// Hand-written conformance fixture (this repo).
module diff-cross-context-empty {
  yang-version 1.1;
  namespace "urn:vibe-ports:yang:diff-cross-context-empty";
  prefix dcce;
  container top {
    presence "retain empty parent";
    leaf label { type string; }
    leaf-list text { type string; }
    leaf-list binary { type binary; }
    leaf-list empty { type empty; }
    leaf-list union { type union { type string; type uint8; } }
    list entry {
      key "a b";
      leaf a { type string; }
      leaf b { type string; }
    }
    leaf-list user { type string; ordered-by user; }
  }
}
