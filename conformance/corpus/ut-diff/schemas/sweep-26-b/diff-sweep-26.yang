// SPDX-License-Identifier: BSD-3-Clause
// Deterministically generated conformance fixture (this repo).
module diff-sweep-26 {
  yang-version 1.1;
  namespace "urn:vibe-ports:yang:ut-diff:sweep:26";
  prefix ds26;

  container top {
    leaf c0 { type string; }
    leaf-list c1 { type string; ordered-by user; }
    list c2 {
      key "key";
      leaf key { type string; }
      leaf value { type string; }
    }
    leaf c3 { type string; }
    leaf-list c4 { type int8; ordered-by system; }
  }
}
