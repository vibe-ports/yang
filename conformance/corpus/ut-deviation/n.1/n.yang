module n {yang-version 1.1; namespace urn:n;prefix n;leaf a {default test; type string;}leaf b {mandatory true; type string;}deviation /a {deviate add {mandatory true;} deviate delete {default test;}}deviation /b {deviate add {default test;} deviate replace {mandatory false;}}}
