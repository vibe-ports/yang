module o {namespace urn:o;prefix o;leaf-list a {type string;}list b {config false;}leaf-list c {min-elements 1; max-elements 10; type string;}list d {min-elements 10; max-elements 100; config false;}deviation /a {deviate add {min-elements 1; max-elements 10;}}deviation /b {deviate add {min-elements 10; max-elements 100;}}deviation /c {deviate replace {min-elements 10; max-elements 100;}}deviation /d {deviate replace {min-elements 1; max-elements 10;}}}
