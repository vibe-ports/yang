module e {yang-version 1.1; namespace urn:e;prefix e; typedef mytype {type string; default nothing;}choice a {default aa;leaf aa {type string;} leaf ab {type string;} leaf ac {type string; mandatory true;}}choice b {default ba;leaf ba {type string;} leaf bb {type string;}}leaf c {default hello; type string;}leaf-list d {default hello; default world; type string;}leaf c2 {type mytype;} leaf-list d2 {type mytype;}}
