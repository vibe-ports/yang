module b {namespace urn:b;prefix b;import a {prefix a;}deviation /a:top/a:b {deviate not-supported;}deviation /a:ch/a:a/a:x {deviate not-supported;}deviation /a:ch/a:c {deviate not-supported;}deviation /a:ch/a:b {deviate not-supported;}deviation /a:ch/a:a/a:a {deviate not-supported;}deviation /a:ch {deviate replace {default a;}}deviation /a:func1/a:input {deviate not-supported;}deviation /a:func1/a:output {deviate not-supported;}deviation /a:func2 {deviate not-supported;}}
