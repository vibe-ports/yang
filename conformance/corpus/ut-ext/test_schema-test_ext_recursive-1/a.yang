module a {
  namespace "urn:a";
  prefix a;

  import b {
    prefix b;
  }

  extension abstract {
    b:use-in "identity";
  }

  identity mount-id;

  identity yang-lib-id {
    base mount-id;
    a:abstract;
  }
}
