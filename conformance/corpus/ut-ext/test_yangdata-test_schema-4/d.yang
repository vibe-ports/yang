module d {yang-version 1.1; namespace urn:tests:extensions:yangdata:d; prefix self;import ietf-restconf {revision-date 2017-01-26; prefix rc;}leaf d { type string;}rc:yang-data template1 { container d {presence d;}}rc:yang-data template2 { container d {presence d;}}}
