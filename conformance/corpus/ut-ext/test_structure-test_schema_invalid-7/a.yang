module a {yang-version 1.1; namespace urn:tests:extensions:structure:a; prefix a;import ietf-yang-structure-ext {prefix sx;}sx:structure struct {  container n1 {leaf l {config false; type uint32;}}  list n2 {leaf l {type string;}}}container n1 {leaf l2 {type uint8;}}}
