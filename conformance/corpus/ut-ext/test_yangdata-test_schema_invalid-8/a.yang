module a {yang-version 1.1; namespace urn:tests:extensions:yangdata:a; prefix self;import ietf-restconf {revision-date 2017-01-26; prefix rc;}grouping t { leaf-list x {type string;}}rc:yang-data template { uses t;}}
