module a {yang-version 1.1; namespace urn:tests:extensions:structure:a; prefix a;import ietf-yang-structure-ext {prefix sx;}sx:structure struct {  must "/n2/l";  status deprecated;  description desc;  reference no-ref;  typedef my-type {type string;}  grouping my-grp {leaf gl {type my-type;}}  container n1 {leaf l {config false; type uint32;}}  list n2 {leaf l {type leafref {path /n1/l;}}}  uses my-grp;}}
