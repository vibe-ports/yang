module a {yang-version 1.1; namespace urn:tests:extensions:metadata:a; prefix a;import ietf-yang-metadata {prefix md;}feature f;md:annotation x {  description "test";  if-feature f;  reference "test";  status "current";  type uint8;  units meters;}}
