module a {yang-version 1.1; namespace urn:tests:extensions:structure:a; prefix self;import ietf-yang-structure-ext {prefix sx;}sx:structure struct { container x { leaf x {type string;}}}choice struct { container y { leaf y {type string;}}}}
