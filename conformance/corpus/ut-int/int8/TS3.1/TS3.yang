module TS3 {
  yang-version 1.1;
  namespace "urn:tests:TS3";
  prefix pref;
typedef my_int_type {   type int8 {range "-100 .. -60 | -1 .. 1 |  60 .. 127";}}leaf my_leaf {type my_int_type {range "-1 .. 1";}}}
