module TS2 {
  yang-version 1.1;
  namespace "urn:tests:TS2";
  prefix pref;
typedef my_int_type {    type int8 {range "-100 .. -60 | -1 .. 1 |  60 .. 120";}}leaf my_leaf {type my_int_type {range "70 .. max";}}}
