module TS_ERR3 {
  yang-version 1.1;
  namespace "urn:tests:TS_ERR3";
  prefix pref;
typedef my_int_type { type int8 {range "-128 .. -60 | -1 .. 1 |  60 .. 127";}}leaf my_leaf {type my_int_type {range "-2 .. 2";}}}
