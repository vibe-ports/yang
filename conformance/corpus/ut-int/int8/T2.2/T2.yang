module T2 {
  yang-version 1.1;
  namespace "urn:tests:T2";
  prefix pref;
leaf port {type int8 {range "0 .. 50 | 105" {        error-app-tag "range-violation";        error-message "invalid range of value";}}}}
