module TS1 {
  yang-version 1.1;
  namespace "urn:tests:TS1";
  prefix pref;
typedef my_int_type {    type int8 {range "-100 .. -60 | -1 .. 1 |  60 .. 127";}}leaf my_leaf {type my_int_type {range "min .. -60";}}}
