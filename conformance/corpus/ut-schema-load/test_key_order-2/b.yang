module b {yang-version 1.1;namespace urn:test:b;prefix b;list l {  key "k1 k2 k3 k4";  leaf k4 {type string;}  container c {    leaf l1 {type string;}  }  leaf k2 {type string;}  leaf l2 {type string;}  leaf k1 {type string;}  leaf k3 {type string;}}}
