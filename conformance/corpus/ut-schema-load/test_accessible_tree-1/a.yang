module a {
    namespace urn:a;
    prefix a;
    container cont {
        leaf l {
            type empty;
        }
    }
    container cont2 {
        leaf l2 {
            must ../../cont/l;
            type leafref {
                path /cont/l;
            }
        }
    }
}
