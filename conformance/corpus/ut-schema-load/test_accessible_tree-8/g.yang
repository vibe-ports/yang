module g {
    namespace urn:g;
    prefix g;
    rpc rp {
        input {
            leaf l {
                type empty;
            }
            leaf l2 {
                must ../l;
                type leafref {
                    path /rp/l;
                }
            }
        }
    }
}
