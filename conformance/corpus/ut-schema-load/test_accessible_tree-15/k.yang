module k {
    yang-version 1.1;
    namespace urn:k;
    prefix k;
    container cont {
        list ll {
            key k;
            leaf k {
                type string;
            }
            action act {
                input {
                    leaf l {
                        type empty;
                    }
                }
                output {
                    leaf l2 {
                        must /cont/ll/act/l;
                        type empty;
                    }
                }
            }
        }
    }
}
