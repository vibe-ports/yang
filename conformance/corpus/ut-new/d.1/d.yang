// SPDX-License-Identifier: BSD-3-Clause
// lyd_change_term statuses: a default leaf (LY_EEXIST when set to its own value) (#98).
module d {
  yang-version 1.1;
  namespace "urn:vibe-ports:yang:ut-new:d";
  prefix d;
  container c {
    leaf x {
      type string;
      default "dflt";
    }
    leaf n {
      type uint8;
    }
  }
}
