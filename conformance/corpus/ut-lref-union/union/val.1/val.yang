module val {
  yang-version 1.1;
  namespace "urn:tests:val";
  prefix pref;
leaf l1 {
  type union {
   type uint32 {
      range "0..1048575";
    }
    type enumeration {
      enum auto;
    }
  }
}
leaf int8 {type int8 {range 10..20;}}
leaf l2 {
  type union {
    type leafref {path /int8; require-instance true;}
    type string;
  }
}
}
