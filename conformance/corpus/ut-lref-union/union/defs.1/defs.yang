module defs {
  yang-version 1.1;
  namespace "urn:tests:defs";
  prefix pref;
identity ident1; identity ident2 {base ident1;}leaf un1 {type union {    type leafref {path /int8; require-instance true;}    type leafref {path /int64; require-instance true;}    type union { type identityref {base ident1;} type instance-identifier {require-instance true;} }    type string {length 1..20;}}}leaf int8 {type int8 {range 10..20;}}leaf int64 {type int64;}leaf-list llist {type string;}}
