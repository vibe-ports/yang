// SPDX-License-Identifier: BSD-3-Clause
// Hand-written oracle fixture for selected-run keyless-list merge behavior.
module pv2-astra305-r9 {
  yang-version 1.1;
  namespace "urn:vibe-ports:yang:conformance:pv2-astra305-r9";
  prefix pa305r9;

  container reply {
    leaf before { type string; }
    list l {
      leaf value { type string; }
    }
    leaf input { type string; }
  }
}
