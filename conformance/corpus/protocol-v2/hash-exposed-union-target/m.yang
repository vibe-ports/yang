// SPDX-License-Identifier: BSD-3-Clause
// Hand-written stored-hash compatibility fixture.
module m { yang-version 1.1; namespace "urn:m"; prefix m;
leaf target {type uint8;} container r {leaf p {type string;} leaf q {type string;} leaf z {type string;}list l {key "a b"; leaf a {type string;} leaf b {type string;}leaf v {type union {type leafref {path "/m:target";} type string;}}}}
}
