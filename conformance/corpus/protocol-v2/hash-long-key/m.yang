// SPDX-License-Identifier: BSD-3-Clause
// Hand-written stored-hash compatibility fixture.
module m { yang-version 1.1; namespace "urn:m"; prefix m;
container r {leaf p {type string;} leaf q {type string;} leaf z {type string;}list l {key k; leaf k {type string;} leaf x {type boolean;} leaf-list v {type string; ordered-by user;}}}
}
