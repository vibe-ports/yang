// SPDX-License-Identifier: BSD-3-Clause
// Hand-written stored-hash compatibility fixture.
module m { yang-version 1.1; namespace "urn:m"; prefix m;
leaf target {type uint8;} container r {leaf p {type string;} leaf q {type string;} leaf z {type string;}list l {key "a"; leaf a {type string;} leaf-list v {type string; ordered-by user;}}}
}
