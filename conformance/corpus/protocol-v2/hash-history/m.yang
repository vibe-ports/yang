// SPDX-License-Identifier: BSD-3-Clause
// Hand-written stored-hash compatibility fixture.
module m { yang-version 1.1; namespace "urn:m"; prefix m;
container r {leaf p {type string;} leaf q {type string;} leaf z {type string;}list l {key k; ordered-by user; leaf k {type binary;} leaf marker {type string;}}}
}
