// SPDX-License-Identifier: BSD-3-Clause
// Hand-written stored-hash compatibility fixture.
module m { yang-version 1.1; namespace "urn:m"; prefix m;
list p {key id; leaf id {type uint32;} leaf a {type string;} leaf b {type string;} list l {key k;leaf k {type string;}}}
}
