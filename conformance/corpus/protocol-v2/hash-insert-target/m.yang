// SPDX-License-Identifier: BSD-3-Clause
// Hand-written conformance fixture (this repo).
module m {
  yang-version 1.1;
  namespace "urn:vibe-ports:yang:conformance:hash-insert";
  prefix m;

  container r {
    leaf y { type string; }
    leaf between { type string; }
    leaf z { type string; }
    leaf-list x { type uint8; }
    list l {
      key "k";
      leaf k { type uint8; }
    }
    leaf-list u {
      type uint8;
      ordered-by user;
    }
  }
}
