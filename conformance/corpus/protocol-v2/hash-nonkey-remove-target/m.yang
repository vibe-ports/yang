// SPDX-License-Identifier: BSD-3-Clause
// Hand-written stored-hash compatibility fixture.
module m {
  yang-version 1.1;
  namespace "urn:m";
  prefix m;

  container r {
    list l {
      config false;
      key "b";
      leaf a { type string; }
      leaf b { type string; }
    }
  }
}
