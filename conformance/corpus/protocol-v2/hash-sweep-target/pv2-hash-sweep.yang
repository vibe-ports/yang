// SPDX-License-Identifier: BSD-3-Clause
// Hand-written conformance fixture (this repo).
module pv2-hash-sweep {
  yang-version 1.1;
  namespace "urn:hash-sweep";
  prefix hs;
  import ietf-inet-types { prefix inet; }
  import ietf-yang-types { prefix yang; }
  import ietf-netconf-acm { prefix nacm; }
  import libnetconf2-netconf-server { prefix nc; }
  import yang { prefix y; }

  container r {
    leaf number { type uint32; }
    leaf word { type string; }
    leaf-list lyb-uint8-zero { config false; type uint8; }
    leaf-list lyb-uint8-positive { config false; type uint8; }
    leaf-list lyb-uint16-zero { config false; type uint16; }
    leaf-list lyb-uint16-positive { config false; type uint16; }
    leaf-list lyb-uint32-zero { config false; type uint32; }
    leaf-list lyb-uint32-positive { config false; type uint32; }
    leaf-list lyb-uint64-zero { config false; type uint64; }
    leaf-list lyb-uint64-positive { config false; type uint64; }
    leaf-list lyb-int8-zero { config false; type int8; }
    leaf-list lyb-int8-positive { config false; type int8; }
    leaf-list lyb-int8-negative { config false; type int8; }
    leaf-list lyb-int8-minimum { config false; type int8; }
    leaf-list lyb-int16-zero { config false; type int16; }
    leaf-list lyb-int16-positive { config false; type int16; }
    leaf-list lyb-int16-negative { config false; type int16; }
    leaf-list lyb-int16-minimum { config false; type int16; }
    leaf-list lyb-int32-zero { config false; type int32; }
    leaf-list lyb-int32-positive { config false; type int32; }
    leaf-list lyb-int32-negative { config false; type int32; }
    leaf-list lyb-int32-minimum { config false; type int32; }
    leaf-list lyb-int64-zero { config false; type int64; }
    leaf-list lyb-int64-positive { config false; type int64; }
    leaf-list lyb-int64-negative { config false; type int64; }
    leaf-list lyb-int64-minimum { config false; type int64; }
    leaf-list lyb-decimal-zero { config false; type decimal64 { fraction-digits 2; } }
    leaf-list lyb-decimal-positive { config false; type decimal64 { fraction-digits 2; } }
    leaf-list lyb-decimal-negative { config false; type decimal64 { fraction-digits 2; } }
    leaf-list lyb-boolean-true { config false; type boolean; }
    leaf-list lyb-boolean-false { config false; type boolean; }
    leaf-list lyb-binary { config false; type binary; }
    leaf-list text-binary-empty { config false; type binary; }
    leaf-list lyb-bits-empty { config false; type bits { bit low { position 0; } bit high { position 17; } } }
    leaf-list lyb-bits-low { config false; type bits { bit low { position 0; } bit high { position 17; } } }
    leaf-list lyb-bits-high { config false; type bits { bit low { position 0; } bit high { position 17; } } }
    leaf-list lyb-bits-both { config false; type bits { bit low { position 0; } bit high { position 17; } } }
    leaf-list lyb-enum-zero-width { config false; type enumeration { enum keep { value 0; } } }
    leaf-list lyb-enum-positive { config false; type enumeration { enum keep { value 1; } enum high { value 256; } } }
    leaf-list lyb-enum-negative-declaration { config false; type enumeration { enum keep { value 1; } enum negative { value -1; } } }
    leaf-list lyb-enum-negative-value { config false; type enumeration { enum negative { value -1; } } }
    leaf-list lyb-leafref-integer { config false; type leafref { path "../number"; require-instance false; } }
    leaf-list text-leafref-string { config false; type leafref { path "../word"; require-instance false; } }
    leaf-list lyb-union-int { config false; type union { type int32; type string; } }
    leaf-list lyb-union-string { config false; type union { type int32; type string; } }
    leaf-list lyb-union-empty { config false; type union { type empty; type string; } }
    leaf-list lyb-union-binary-empty { config false; type union { type binary; type string; } }
    leaf-list lyb-union-nested-int { config false; type union { type boolean; type union { type int32; type string; } } }
    leaf-list lyb-union-nested-string { config false; type union { type boolean; type union { type int32; type string; } } }
    leaf-list lyb-union-leafref { config false; type union { type leafref { path "../number"; require-instance false; } type string; } }
    leaf-list lyb-ipv4-plain { config false; type inet:ipv4-address; }
    leaf-list lyb-ipv4-numeric-zone { config false; type inet:ipv4-address; }
    leaf-list lyb-ipv4-named-zone { config false; type inet:ipv4-address; }
    leaf-list lyb-ipv4-link-local { config false; type inet:ipv4-address-link-local; }
    leaf-list lyb-ipv4-no-zone { config false; type inet:ipv4-address-no-zone; }
    leaf-list lyb-ipv4-prefix { config false; type inet:ipv4-prefix; }
    leaf-list lyb-ipv4-host-prefix { config false; type inet:ipv4-address-and-prefix; }
    leaf-list lyb-ip-address-v4 { config false; type inet:ip-address; }
    leaf-list lyb-ip-no-zone-v4 { config false; type inet:ip-address-no-zone; }
    leaf-list lyb-ip-prefix-v4 { config false; type inet:ip-prefix; }
    leaf-list lyb-ip-host-prefix-v4 { config false; type inet:ip-address-and-prefix; }
    leaf-list lyb-ip-link-local-v4 { config false; type inet:ip-address-link-local; }
    leaf-list lyb-ip-address-v6 { config false; type inet:ip-address; }
    leaf-list lyb-ip-no-zone-v6 { config false; type inet:ip-address-no-zone; }
    leaf-list lyb-ip-prefix-v6 { config false; type inet:ip-prefix; }
    leaf-list lyb-ip-host-prefix-v6 { config false; type inet:ip-address-and-prefix; }
    leaf-list lyb-ip-link-local-v6 { config false; type inet:ip-address-link-local; }
    leaf-list lyb-ipv6-plain { config false; type inet:ipv6-address; }
    leaf-list lyb-ipv6-numeric-zone { config false; type inet:ipv6-address; }
    leaf-list lyb-ipv6-named-zone { config false; type inet:ipv6-address; }
    leaf-list lyb-ipv6-link-local { config false; type inet:ipv6-address-link-local; }
    leaf-list lyb-ipv6-no-zone { config false; type inet:ipv6-address-no-zone; }
    leaf-list lyb-ipv6-prefix { config false; type inet:ipv6-prefix; }
    leaf-list lyb-ipv6-host-prefix { config false; type inet:ipv6-address-and-prefix; }
    leaf-list lyb-dt-new-known { config false; type yang:date-and-time; }
    leaf-list lyb-dt-new-positive-offset { config false; type yang:date-and-time; }
    leaf-list lyb-dt-new-negative-offset { config false; type yang:date-and-time; }
    leaf-list lyb-dt-new-fraction-known { config false; type yang:date-and-time; }
    leaf-list lyb-dt-new-fraction-offset { config false; type yang:date-and-time; }
    leaf-list lyb-dt-new-unknown { config false; type yang:date-and-time; }
    leaf-list lyb-dt-new-fraction-unknown { config false; type yang:date-and-time; }
    leaf-list lyb-dt-new-z-input { config false; type yang:date-and-time; }
    leaf-list lyb-dt-new-minus-zero-input { config false; type yang:date-and-time; }
    leaf-list lyb-date-known { config false; type yang:date; }
    leaf-list lyb-date-unknown { config false; type yang:date; }
    leaf-list lyb-date-positive-offset { config false; type yang:date; }
    leaf-list lyb-date-negative-offset { config false; type yang:date; }
    leaf-list lyb-date-no-zone { config false; type yang:date-no-zone; }
    leaf-list lyb-time-known { config false; type yang:time; }
    leaf-list lyb-time-offset { config false; type yang:time; }
    leaf-list lyb-time-fraction-known { config false; type yang:time; }
    leaf-list lyb-time-fraction-offset { config false; type yang:time; }
    leaf-list lyb-time-unknown { config false; type yang:time; }
    leaf-list lyb-time-fraction-unknown { config false; type yang:time; }
    leaf-list lyb-time-no-zone { config false; type yang:time-no-zone; }
    leaf-list lyb-time-no-zone-fraction { config false; type yang:time-no-zone; }
    leaf-list text-string { config false; type string; }
    leaf-list text-string-empty { config false; type string; }
    leaf-list text-empty { config false; type empty; }
    leaf-list text-hex { config false; type yang:hex-string; }
    leaf-list text-phys { config false; type yang:phys-address; }
    leaf-list text-mac { config false; type yang:mac-address; }
    leaf-list text-uuid { config false; type yang:uuid; }
    leaf-list text-xpath { config false; type yang:xpath1.0; }
    leaf-list text-instanceid { config false; type instance-identifier { require-instance false; } }
    leaf-list text-node-instanceid { config false; type nacm:node-instance-identifier; }
    leaf-list text-node-instanceid-root { config false; type nacm:node-instance-identifier; }
    leaf-list text-instanceid-keys { config false; type y:instance-identifier-keys; }
    leaf-list text-time-period { config false; type nc:time-period; }
  }
}
