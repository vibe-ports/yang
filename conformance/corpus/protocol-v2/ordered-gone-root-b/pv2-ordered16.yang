// SPDX-License-Identifier: BSD-3-Clause
// Hand-written conformance fixture (this repo).
module pv2-ordered16 {
  yang-version 1.1;
  namespace "urn:vibe-ports:yang:conformance:pv2-ordered16";
  prefix o16;

  description
    "Hand-written (this repo): a top-level node that the when pass deletes
     ahead of an equal node of another context (design 15).";

  leaf guard {
    type string;
    when "/o16:x";
  }
  leaf x {
    type string;
  }
}
