module pv2-ordered9 {
  yang-version 1.1;
  namespace "urn:vibe-ports:yang:conformance:pv2-ordered9";
  prefix o9;

  description
    "Hand-written (this repo): c/l directly under c; schemas/pv2-ordered9
     holds the same module with c/l inside a choice (design 15).";

  container c {
    leaf a {
      type string;
    }
    list l {
      key "k";
      leaf k {
        type string;
      }
    }
    leaf b {
      type string;
    }
  }
}
