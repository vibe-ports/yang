module pv2-must-message {
  yang-version 1.1;
  namespace "urn:vibe-ports:yang:conformance:pv2-must-message";
  prefix pmm;

  description
    "A failing must whose error-message matches an internal XPath diagnostic.";

  container c {
    must "false()" {
      error-message "Internal error (xpath.c:1348).";
    }
  }
}
