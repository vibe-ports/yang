// SPDX-License-Identifier: BSD-3-Clause
// Hand-written conformance fixture (this repo).
module pv2-bytebits {
  yang-version 1.1;
  namespace "urn:vibe-ports:yang:conformance:pv2-bytebits";
  prefix bb;

  leaf-list v {
    config false;
    type bits { bit a { position 0; } }
  }
}
