// A diff that deletes one state leaf-list duplicate and annotates the others: each next first
// instance must find its duplicates among the live siblings (lyd_dup_inst_next).
module pv2-dupinst {
  yang-version 1.1;
  namespace "urn:vibe-ports:yang:conformance:pv2-dupinst";
  prefix pdi;
  import ietf-yang-metadata { prefix md; }
  md:annotation note { type string; }
  container c {
    leaf a { type string; }
    leaf b { type string; }
    leaf d { type string; }
    leaf-list sl { config false; type int32; }
  }
}
