// SPDX-License-Identifier: BSD-3-Clause
// Hand-written conformance fixture (this repo).
module pv2-hash-lookup {
  yang-version 1.1;
  namespace "urn:vibe-ports:yang:conformance:pv2-hash-lookup";
  prefix phl;
  grouping nodes {
    leaf a { type string; }
    leaf b { type string; }
    leaf c { type string; }
    list l {
      key k;
      leaf k { type string; }
      leaf v { type string; }
    }
  }
  uses nodes;
  container r { uses nodes; }
}
