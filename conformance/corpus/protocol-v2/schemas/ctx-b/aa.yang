// SPDX-License-Identifier: BSD-3-Clause
// Hand-written conformance fixture (this repo).
module aa {
  yang-version 1.1;
  namespace "urn:vibe-ports:yang:conformance:aa";
  prefix aa;
  leaf keep { type string; }
}
