module pv2-ordered14 {
  yang-version 1.1;
  namespace "urn:vibe-ports:yang:conformance:pv2-ordered14";
  prefix o14;

  description
    "Hand-written (this repo): a positional instance-identifier into a
     leaf-list run that a when-deleted node separates (design 15).";

  leaf guard {
    config false;
    type string;
    when "deref(../ref)";
  }
  leaf ref {
    config false;
    type instance-identifier;
  }
  container c {
    config false;
    leaf-list s {
      type uint32;
    }
    leaf x {
      type string;
      when "false()";
    }
    leaf f1 { type string; }
    leaf f2 { type string; }
    leaf f3 { type string; }
  }
}
