module pv2-yang-loader {
  yang-version 1.1;
  namespace "urn:vibe-ports:yang:conformance:pv2-yang-loader";
  prefix pyl;

  import yang {
    prefix yang;
    revision-date 2026-01-01;
  }

  description
    "Loads a newer import-only revision of yang beside libyang's implemented revision.";

  leaf marker {
    type yang:marker;
  }
}
