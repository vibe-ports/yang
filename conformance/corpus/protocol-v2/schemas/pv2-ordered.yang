module pv2-ordered {
  yang-version 1.1;
  namespace "urn:vibe-ports:yang:conformance:pv2-ordered";
  prefix o;

  description
    "Hand-written (this repo): input order under LYD_PARSE_ORDERED.";

  container c {
    leaf a {
      type string;
    }
    leaf b {
      type string;
    }
  }
}
