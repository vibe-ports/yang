module pv2-sort-keys {
  yang-version 1.1;
  namespace "urn:vibe-ports:yang:conformance:pv2-sort-keys";
  prefix psk;

  container c {
    list l {
      key "a b";
      leaf a { type string; }
      leaf b { type string; }
    }
  }
}
