// SPDX-License-Identifier: BSD-3-Clause
module pv2-rejected {
  yang-version 1.1;
  namespace "urn:vibe-ports:yang:conformance:pv2-rejected";
  prefix rejected;
  description "Hand-written rejected schema for request-initializer ordering.";
  leaf bad { type uint8; default 256; }
}
