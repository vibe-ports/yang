module pv2-aug {
  yang-version 1.1;
  namespace "urn:vibe-ports:yang:conformance:pv2-aug";
  prefix pa;

  import pv2 {
    prefix p;
  }

  description
    "Hand-written cross-module augment of pv2 (when on augment, uses of a foreign grouping).";

  augment "/p:c" {
    when "p:mode = 'on'";
    leaf extra {
      type string;
    }
    uses p:from-group {
      refine grouped {
        default "g";
      }
    }
  }
}
