// SPDX-License-Identifier: BSD-3-Clause
module pv2-empty-rev-broken-import {
  yang-version 1.1;
  namespace "urn:vibe-ports:yang:conformance:pv2-empty-rev-broken-import";
  prefix erbi;

  import pv2-empty-rev-broken-dep { prefix broken; }

  revision 2020-01-03;
}
