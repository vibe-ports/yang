module pv2-ordered3 {
  yang-version 1.1;
  namespace "urn:vibe-ports:yang:conformance:pv2-ordered3";
  prefix o3;

  description
    "Hand-written (this repo): top-level leaves for LYD_PARSE_ORDERED XPath
     lookups past an opaque root (design 15).";

  leaf a {
    type string;
  }
  leaf b {
    type string;
  }
  leaf-list st {
    config false;
    type uint8;
  }
}
