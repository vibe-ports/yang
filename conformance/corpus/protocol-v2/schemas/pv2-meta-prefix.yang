module pv2-meta-prefix {
  yang-version 1.1;
  namespace "urn:vibe-ports:yang:conformance:pv2-meta-prefix";
  prefix pm;
  import ietf-yang-metadata { prefix md; }

  md:annotation meta-note { type string; }

  container c {}
  list l {
    key k;
    leaf k { type string; }
  }
}
