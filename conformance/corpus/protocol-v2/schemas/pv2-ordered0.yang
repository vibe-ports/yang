module pv2-ordered0 {
  yang-version 1.1;
  namespace "urn:vibe-ports:yang:conformance:pv2-ordered0";
  prefix o0;

  description
    "Hand-written (this repo): a module sorted before the others whose
     defaulted leaf is created in a LYD_PARSE_ORDERED top level out of
     module order (design 15).";

  leaf b {
    type string;
  }
  leaf c {
    type string;
    default "d";
  }
}
