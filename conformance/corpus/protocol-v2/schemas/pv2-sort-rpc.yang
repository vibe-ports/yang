module pv2-sort-rpc {
  yang-version 1.1;
  namespace "urn:vibe-ports:yang:conformance:pv2-sort-rpc";
  prefix psr;

  rpc r {
    input {
      list l {
        key k;
        leaf k { type int32; }
      }
    }
  }

  container c {
    list l {
      key k;
      leaf k { type int32; }
    }
  }
}
