// SPDX-License-Identifier: BSD-3-Clause
module pv2-empty-rev-parse {
  yang-version 1.1;
  namespace "urn:vibe-ports:yang:conformance:pv2-empty-rev-parse";
  prefix erp;

  include pv2-empty-rev-parse-sub;

  revision 2020-01-01;
}
