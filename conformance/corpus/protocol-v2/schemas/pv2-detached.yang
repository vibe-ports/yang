module pv2-detached {
  yang-version 1.1;
  namespace "urn:vibe-ports:yang:conformance:pv2-detached";
  prefix pd;

  description
    "Top-level user-ordered instances used to exercise detached-node APIs.";

  feature extra;

  list l {
    key k;
    ordered-by user;
    leaf k { type string; }
  }

  leaf-list ll {
    type string;
    ordered-by user;
  }

  leaf-list sll {
    config false;
    type string;
    ordered-by user;
  }

  container c {
    leaf base { type string; }
    leaf extra { if-feature extra; type string; }
    list l {
      key k;
      ordered-by user;
      leaf k { type string; }
    }

    leaf-list ll {
      type string;
      ordered-by user;
    }
  }
}
