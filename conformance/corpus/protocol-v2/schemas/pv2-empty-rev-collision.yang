// SPDX-License-Identifier: BSD-3-Clause
module pv2-empty-rev-collision {
  yang-version 1.1;
  namespace "urn:vibe-ports:yang:conformance:pv2-empty-rev-collision";
  prefix erc;

  include pv2-empty-rev-collision-a;

  revision 2020-01-04;
}
