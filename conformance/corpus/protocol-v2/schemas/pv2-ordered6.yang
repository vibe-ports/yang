module pv2-ordered6 {
  yang-version 1.1;
  namespace "urn:vibe-ports:yang:conformance:pv2-ordered6";
  prefix o6;

  description
    "Hand-written (this repo): a top-level choice whose old case holds two
     leaves, kept out of schema order by LYD_PARSE_ORDERED (design 15).";

  choice ch {
    case k1 {
      leaf a {
        type string;
      }
      leaf b {
        type string;
      }
    }
    case k2 {
      leaf c {
        type string;
      }
    }
  }
}
