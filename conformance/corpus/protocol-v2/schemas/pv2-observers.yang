// SPDX-License-Identifier: BSD-3-Clause
module pv2-observers {
  yang-version 1.1;
  namespace "urn:pv2-observers";
  prefix o;

  typedef first-int { type int8 { range "1..3"; } }
  typedef second-int { type int8; }

  container c {
    leaf strings {
      type union {
        type string;
        type string { length "1..3"; }
      }
    }
    leaf integers {
      type union {
        type first-int;
        type second-int;
      }
    }
    leaf target { type second-int; }
    leaf ref { type leafref { path "../target"; } }
    leaf reference {
      type union {
        type leafref { path "../target"; }
        type string;
      }
    }
    leaf shared {
      type union {
        type leafref { path "../target"; }
        type second-int;
        type string;
      }
    }
    leaf nested {
      type union {
        type boolean;
        type union {
          type first-int;
          type second-int;
        }
      }
    }
  }
}
