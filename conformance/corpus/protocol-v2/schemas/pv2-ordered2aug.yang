module pv2-ordered2aug {
  yang-version 1.1;
  namespace "urn:vibe-ports:yang:conformance:pv2-ordered2aug";
  prefix o2a;

  import pv2-ordered2 {
    prefix o2;
  }

  description
    "Hand-written (this repo): a leaf with the local name of the list it
     separates, augmented into pv2-ordered2's container (design 15).";

  augment "/o2:c" {
    leaf l {
      type string;
    }
  }
}
