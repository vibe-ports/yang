// SPDX-License-Identifier: BSD-3-Clause
// Hand-written conformance fixture (this repo).
module pv2-union-key-members {
  yang-version 1.1;
  namespace "urn:vibe-ports:yang:conformance:pv2-union-key-members";
  prefix ukm;

  container c {
    list l {
      key "k";
      leaf k {
        type union {
          type int8;
          type string;
        }
      }
      leaf v {
        type string;
      }
    }
  }
}
