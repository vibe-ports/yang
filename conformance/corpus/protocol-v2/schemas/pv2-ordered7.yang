module pv2-ordered7 {
  yang-version 1.1;
  namespace "urn:vibe-ports:yang:conformance:pv2-ordered7";
  prefix o7;

  description
    "Hand-written (this repo): top-level leaf-list defaults created after an
     opaque LYD_PARSE_ORDERED root (design 15).";

  leaf x {
    type string;
  }
  leaf-list d {
    type uint8;
    default "3";
    default "1";
  }
}
