module pv2-cm {
  yang-version 1.1;
  namespace "urn:pv2-cm";
  prefix m;

  import pv2-cg { prefix gg; }
  import pv2-cb { prefix b; }

  description
    "Hand-written (issue #90): uses pv2-cg's grouping (an identity gid of its own
     too), and a must whose literal has an import prefix only after concat():
     a prefix not written in the expression is not in its prefix data.";

  identity gid { base gg:base; }

  container c {
    uses gg:grp;
    leaf id2 { type identityref { base b:base-id; } }
    leaf mc { type string; must "../id2 = concat('b', ':one')"; }
  }
}
