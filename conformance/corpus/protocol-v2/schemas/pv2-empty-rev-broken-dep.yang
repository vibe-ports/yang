// SPDX-License-Identifier: BSD-3-Clause
module pv2-empty-rev-broken-dep {
  yang-version 1.1;
  namespace "urn:vibe-ports:yang:conformance:pv2-empty-rev-broken-dep";
  prefix erbd;

  leaf broken { type ; }
}
