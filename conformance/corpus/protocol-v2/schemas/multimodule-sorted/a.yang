// SPDX-License-Identifier: BSD-3-Clause
// Hand-written conformance fixture (this repo).
module a {
  yang-version 1.1;
  namespace "urn:vibe-ports:yang:multimodule-sorted:a";
  prefix a;

  leaf first {
    type string;
  }
}
