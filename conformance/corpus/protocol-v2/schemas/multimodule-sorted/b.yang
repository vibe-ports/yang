// SPDX-License-Identifier: BSD-3-Clause
// Hand-written conformance fixture (this repo).
module b {
  yang-version 1.1;
  namespace "urn:vibe-ports:yang:multimodule-sorted:b";
  prefix b;

  leaf-list ll {
    ordered-by system;
    type uint8;
  }

  list l {
    key "k";
    ordered-by system;
    leaf k {
      type uint8;
    }
  }

  container c {
    leaf-list ll {
      ordered-by system;
      type uint8;
    }
    list l {
      key "k";
      ordered-by system;
      leaf k {
        type uint8;
      }
    }
  }
}
