module a {namespace urn:tests:a;prefix a;yang-version 1.1;revision 2014-05-08;leaf bar {type string;}list l1 { key "a b"; leaf a {type string;} leaf b {type string;} leaf c {type string;}}leaf foo { type string;}leaf-list ll { type string;}container c {leaf-list x {type string;}}anydata any {config false;}list l2 {config false;    container c{leaf x {type string;} leaf-list d {type string;}}}}
