module T5 {
  yang-version 1.1;
  namespace "urn:tests:T5";
  prefix pref;
list rule {key "id";unique "name";unique "ip port";leaf id{type int32;}leaf name{type string;}leaf ip{type string;}leaf port{type int16;}}}
