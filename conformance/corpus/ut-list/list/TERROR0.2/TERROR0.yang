module TERROR0 {
  yang-version 1.1;
  namespace "urn:tests:TERROR0";
  prefix pref;
list "" {key uid;unique name;ordered-by system;leaf uid{type int32;}leaf name{type string;}leaf group{type string;}}}
