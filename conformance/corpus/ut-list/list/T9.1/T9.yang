module T9 {
  yang-version 1.1;
  namespace "urn:tests:T9";
  prefix pref;
list user {key uid;unique name;ordered-by system;leaf uid{type int32;}leaf name{type string;}leaf group{type string; default "abcd";}}}
