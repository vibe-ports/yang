module T_EMPTY_LIST {
  yang-version 1.1;
  namespace "urn:tests:T_EMPTY_LIST";
  prefix pref;
container user_list {   list user {   key uid;   unique "name group";   leaf uid{type uint32;}   leaf name{type string;}   leaf group{type string;}}}}
