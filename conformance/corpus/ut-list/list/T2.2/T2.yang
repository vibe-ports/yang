module T2 {
  yang-version 1.1;
  namespace "urn:tests:T2";
  prefix pref;
list user {   key uid;   min-elements 3;   max-elements 5;   leaf uid{type uint32;}   leaf name{type string;}   leaf group{type string;}}}
