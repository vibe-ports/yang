module T2 {
  yang-version 1.1;
  namespace "urn:tests:T2";
  prefix pref;
typedef my_type {type string {pattern "[A-Za-z]*"{description   "pattern description";error-app-tag "pattern err-apt-tag";error-message "pattern error message";}}}leaf port {type my_type{pattern "[A-Z]*";}}}
