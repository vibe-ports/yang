module T1 {
  yang-version 1.1;
  namespace "urn:tests:T1";
  prefix pref;
typedef my_type {type string {pattern "[A-Za-z]*"{description   "pattern description";error-app-tag "pattern err-apt-tag";error-message "pattern error message";}}}leaf port {type my_type;}}
