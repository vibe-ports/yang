module T0 {
  yang-version 1.1;
  namespace "urn:tests:T0";
  prefix pref;
leaf port {type string {pattern "[A-Za-z]*"{description   "pattern description";error-app-tag "pattern err-apt-tag";error-message "pattern error message";}}}}
