module TRANGE_0 {
  yang-version 1.1;
  namespace "urn:tests:TRANGE_0";
  prefix pref;
leaf port {type int8 {range "0 .. 50 | 126"{description   "description test";error-app-tag "err-apt-tag";error-message "error message";}}}}
