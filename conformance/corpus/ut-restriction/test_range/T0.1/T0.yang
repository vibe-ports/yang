module T0 {
  yang-version 1.1;
  namespace "urn:tests:T0";
  prefix pref;
leaf port {type int8 {range "0 .. 50 | 127"{description   "description test";error-app-tag "err-apt-tag";error-message "error message";}}}}
