module T1 {
  yang-version 1.1;
  namespace "urn:tests:T1";
  prefix pref;
typedef my_type {type uint16 {range "0 .. 100"{description   "percentage";error-app-tag "err-apt-tag";error-message "error message";}}}leaf port {type my_type;}}
