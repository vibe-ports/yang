module T1 {
  yang-version 1.1;
  namespace "urn:tests:T1";
  prefix pref;
leaf port {type string {       length  "5 .. 10 | 20";       pattern '[a-zA-Z_][a-zA-Z0-9\-_.<]*' ;       pattern 'p4.*' {modifier invert-match;           error-app-tag "pattern-violation"; error-message "invalid pattern of value";}}}}
